FME workspace BestPracticeReportGenerator2017.fmw

Parameters:
- SourceDataset_FMW = C:\Users\imark\Google Drive\2016 - Best Practice Analysis\ReaderWriterFTConnectionTest.fmw   # FME Workspace file to be analysed
- DestDataset_HTML = $(FME_MF_DIR)BestPracticeReportGenerator2017.html   # HTML Files(*.html)|*.html HTML report file
- ReportName = Workspace Test   # Enter a name for the report

Readers:
- FMW_1: FMW from $(SourceDataset_FMW)

Writers:
- HTML_1: HTML to $(DestDataset_HTML)

Transformers (reader FMW_1)
    attributes: workspace_id uint32, transformer_id uint32, transformer_name string, transformer_type string, current_transformer_version uint8, max_transformer_version uint8, transformer_enabled logical, transformer_last_edit_build_number uint32
    -> Junction_23
    -> Junction_39
    -> Junction_60
Note: WriterAnalysis
Junction_60
    -> BestPractice:WriterAnalysis [Input:Transformers]
Note: PerformanceAnalysis
Junction_39
    -> BestPractice-PerformanceAnalysis [Input:Transformers]
Note: TransformerAnalysis
Junction_23
    -> BestPractice-TransformerAnalysis [Input:Transformers]
TransformerParameters (reader FMW_1)
    attributes: workspace_id uint32, transformer_id uint32, transformer_parameter_name string, transformer_parameter_value string
    -> Junction_25
    -> Junction_42
Note: Performance:Analysis
Junction_42
    -> BestPractice-PerformanceAnalysis [Input:TransformerParameters]
BestPractice-PerformanceAnalysis
    TRANSFORMER_ENABLED = @Value(transformer_enabled)
    WORKSPACE_ID = @Value(workspace_id)
    TRANSFORMER_TYPE = @Value(transformer_type)
    TRANSFORMER_NAME = @Value(transformer_name)
    TRANSFORMER_ID = @Value(transformer_id)
    TRANSFORMER_PARAMETER_VALUE = @Value(transformer_parameter_value)
    TRANSFORMER_PARAMETER_NAME = @Value(transformer_parameter_name)
    TRANSFORMER_LAST_EDIT_BUILD_NUMBER = @Value(transformer_last_edit_build_number)
    CURRENT_TRANSFORMER_VERSION = @Value(current_transformer_version)
    MAX_TRANSFORMER_VERSION = @Value(max_transformer_version)
    Output:Report -> Junction_2
    Output:Summary -> Junction
Note: TransformerAnalysis
Junction_25
    -> BestPractice-TransformerAnalysis [Input:TransformerParameters]
PublishedParameters (reader FMW_1)
    attributes: workspace_id uint32, published_parameter_name string, published_parameter_type string, published_parameter_default_value string
    -> Junction_71
    -> Junction_73
Note: ReaderAnalysis
Junction_71
    -> BestPractice-ReaderAnalysis [Input:PublishedParameters]
Note: WriterAnalysis
Junction_73
    -> BestPractice:WriterAnalysis [Input:PublishedParameters]
WriterFeatureTypes (reader FMW_1)
    attributes: workspace_id uint32, writer_id uint32, feature_type_id uint32, writer_feature_type_qualifier string, writer_feature_type_name string, writer_feature_type_possible_geometries string, writer_feature_type_enabled logical
    -> BestPractice:WriterAnalysis [Input:WriterFeatureTypes]
Note: WriterAnalysis
FeatureTypeUserAttributes (reader FMW_1)
    attributes: workspace_id uint32, feature_type_id uint32, user_attribute_name string, user_attribute_type string
    -> BestPractice:WriterAnalysis [Input:FeatureTypeUserAttributes]
Note: WriterAnalysis
Writers (reader FMW_1)
    attributes: workspace_id uint32, writer_id uint32, writer_name string, writer_keyword string, writer_type string, destination_dataset string, writer_enabled logical, writer_generate_build_number uint32
    -> BestPractice:WriterAnalysis [Input:Writers]
Note: WorkspaceAnalysis
WorkspaceProperties (reader FMW_1)
    attributes: workspace_id uint32, workspace_name string, modified_build_number uint32, category string, usage string, history string, requirement string, requirements_flag string
    -> BestPractice-WorkspaceAnalysis [Input:WorkspaceProperties]
BestPractice-WorkspaceAnalysis
    USAGE = @Value(usage)
    WORKSPACE_ID = @Value(workspace_id)
    CATEGORY = @Value(category)
    HISTORY = @Value(history)
    MODIFIED_BUILD_NUMBER = @Value(modified_build_number)
    REQUIREMENTS_FLAG = @Value(requirements_flag)
    REQUIREMENT = @Value(requirement)
    WORKSPACE_NAME_2 = @Value(workspace_name)
    Output:Report -> Junction_2
    Output:Summary -> Junction
ReaderFeatureTypes (reader FMW_1)
    attributes: workspace_id uint32, reader_id uint32, feature_type_id uint32, reader_feature_type_qualifier string, reader_feature_type_name string, reader_feature_type_possible_geometries string, reader_feature_type_enabled logical
    -> Junction_14
Note: ReaderAnalysis
Junction_14
    -> BestPractice-ReaderAnalysis [Input:ReaderFeatureTypes]
ReaderParameters (reader FMW_1)
    attributes: workspace_id uint32, reader_id uint32, reader_parameter_name string, reader_parameter_value string
    -> BestPractice:WriterAnalysis [Input:ReaderParameters]
FileProperties (reader FMW_1)
    attributes: workspace_id uint32, file_path string, file_size uint64, creation_date datetime, modified_date datetime, last_run_date datetime
    -> FilenamePartExtractor
FilenamePartExtractor
    DIRPATH_ATTR = ReportWorkspacePath
    SRC_ATTR = $(SourceDataset_FMW)
    DIRNAME_ATTR = ReportWorkspaceFolder
    FULLNAME_ATTR = ReportWorkspaceName
    -> AttributeManager
AttributeManager
    ATTR_TABLE:
      SET_TO ReportName = $(ReportName)
      RENAME_SET_VALUE file_size > ReportWorkspaceSize
      RENAME_SET_VALUE creation_date > ReportWorkspaceCreation
      RENAME_SET_VALUE modified_date > ReportWorkspaceModified
      RENAME_SET_VALUE last_run_date > ReportWorkspaceLastRun
    -> BestPractice-ReportHeader
BestPractice-ReportHeader
    REPORTWORKSPACEMODIFIED = @Value(ReportWorkspaceModified)
    REPORTWORKSPACESIZE = @Value(ReportWorkspaceSize)
    REPORTWORKSPACEFOLDER = @Value(ReportWorkspaceFolder)
    REPORTWORKSPACECREATION = @Value(ReportWorkspaceCreation)
    REPORTWORKSPACEPATH = @Value(ReportWorkspacePath)
    REPORTNAME = @Value(ReportName)
    REPORTWORKSPACELASTRUN = @Value(ReportWorkspaceLastRun)
    REPORTWORKSPACE = @Value(ReportWorkspaceName)
    Output:Report -> Junction_2
Readers (reader FMW_1)
    attributes: workspace_id uint32, reader_id uint32, reader_name string, reader_keyword string, reader_type string, source_dataset string, reader_enabled logical, reader_generate_build_number uint32
    -> Junction_12
Note: ReaderAnalysis
Junction_12
    -> BestPractice-ReaderAnalysis [Input:Readers]
WriterParameters (reader FMW_1)
    attributes: workspace_id uint32, writer_id uint32, writer_parameter_name string, writer_parameter_value string
    -> BestPractice:WriterAnalysis [Input:WriterParameters]
BestPractice:WriterAnalysis
    TRANSFORMER_TYPE = @Value(transformer_type)
    USER_ATTRIBUTE_NAME = @Value(user_attribute_name)
    WRITER_PARAMETER_VALUE = @Value(writer_parameter_value)
    READER_PARAMETER_VALUE = @Value(reader_parameter_value)
    FEATURE_TYPE_ID = @Value(feature_type_id)
    WRITER_ID = @Value(writer_id)
    WRITER_FEATURE_TYPE_NAME = @Value(writer_feature_type_name)
    PUBLISHED_PARAMETER_TYPE = @Value(published_parameter_type)
    WRITER_NAME = @Value(writer_name)
    DESTINATION_DATASET = @Value(destination_dataset)
    WRITER_FEATURE_TYPE_ENABLED = @Value(writer_feature_type_enabled)
    WRITER_ENABLED = @Value(writer_enabled)
    WRITER_TYPE = @Value(writer_type)
    PUBLISHED_PARAMETER_NAME = @Value(published_parameter_name)
    WRITER_FEATURE_TYPE_QUALIFIER = @Value(writer_feature_type_qualifier)
    WRITER_KEYWORD = @Value(writer_keyword)
    READER_PARAMETER_NAME = @Value(reader_parameter_name)
    WORKSPACE_ID = @Value(workspace_id)
    WRITER_FEATURE_TYPE_POSSIBLE_GEOMETRIES = @Value(writer_feature_type_possible_geometries)
    WRITER_PARAMETER_NAME = @Value(writer_parameter_name)
    USER_ATTRIBUTE_TYPE = @Value(user_attribute_type)
    WRITER_GENERATE_BUILD_NUMBER = @Value(writer_generate_build_number)
    PUBLISHED_PARAMETER_DEFAULT_VALUE = @Value(published_parameter_default_value)
    Output:Report -> Junction_2
    Output:Summary -> Junction
Note: Bookmarks and Annotations (Style Analysis)
Statistics (reader FMW_1)
    attributes: workspace_id uint32, num_published_parameters uint32, num_annotations uint32, num_bookmarks uint32, num_breakpoints uint32, num_readers uint32, num_reader_feature_types uint32, num_writers uint32, num_writer_feature_types uint32, num_transformers uint32, num_custom_transformers uint32, num_out_of_date_transformers uint32
    -> BestPractice-StyleAnalysis [Input:Statistics]
BestPractice-StyleAnalysis
    NUM_BOOKMARKS = @Value(num_bookmarks)
    NUM_CUSTOM_TRANSFORMERS = @Value(num_custom_transformers)
    WORKSPACE_ID = @Value(workspace_id)
    NUM_READERS = @Value(num_readers)
    NUM_TRANSFORMERS = @Value(num_transformers)
    NUM_READER_FEATURE_TYPES = @Value(num_reader_feature_types)
    NUM_OUT_OF_DATE_TRANSFORMERS = @Value(num_out_of_date_transformers)
    NUM_ANNOTATIONS = @Value(num_annotations)
    NUM_WRITERS = @Value(num_writers)
    NUM_BREAKPOINTS = @Value(num_breakpoints)
    NUM_WRITER_FEATURE_TYPES = @Value(num_writer_feature_types)
    NUM_PUBLISHED_PARAMETERS = @Value(num_published_parameters)
    Output:Summary -> Junction
    Output:Report -> Junction_2
Note: Breakpoints (Feature Inspection Analysis)
Breakpoints (reader FMW_1)
    attributes: workspace_id uint32, breakpoint_id uint32, breakpoint_name string, breakpoint_condition string, breakpoint_test_clause string, breakpoint_enabled logical
    -> BestPractice-FeatureInspectionAnalysis [Input:Breakpoints]
BestPractice-FeatureInspectionAnalysis: BestPractice-BreakpointAnalysis
    WORKSPACE_ID = @Value(workspace_id)
    BREAKPOINT_ENABLED = @Value(breakpoint_enabled)
    BREAKPOINT_NAME = @Value(breakpoint_name)
    BREAKPOINT_CONDITION = @Value(breakpoint_condition)
    BREAKPOINT_TEST_CLAUSE = @Value(breakpoint_test_clause)
    BREAKPOINT_ID = @Value(breakpoint_id)
    Output:Report -> Junction_2
    Output:Summary -> Junction
Connections (reader FMW_1)
    attributes: connection_id uint32, connection_source_id uint32, connection_target_id uint32, connection_source_port_desc string, connection_target_port_desc string, connection_enabled logical, connection_execution_index uint32, connection_hidden logical
    -> BestPractice-ReaderAnalysis [Input:Connections]
BestPractice-ReaderAnalysis
    READER_TYPE = @Value(reader_type)
    READER_GENERATE_BUILD_NUMBER = @Value(reader_generate_build_number)
    CONNECTION_SOURCE_PORT_DESC = @Value(connection_source_port_desc)
    READER_ID = @Value(reader_id)
    READER_FEATURE_TYPE_ENABLED = @Value(reader_feature_type_enabled)
    FEATURE_TYPE_ID = @Value(feature_type_id)
    PUBLISHED_PARAMETER_TYPE = @Value(published_parameter_type)
    READER_FEATURE_TYPE_POSSIBLE_GEOMETRIES = @Value(reader_feature_type_possible_geometries)
    READER_FEATURE_TYPE_QUALIFIER = @Value(reader_feature_type_qualifier)
    READER_NAME = @Value(reader_name)
    SOURCE_DATASET = @Value(source_dataset)
    PUBLISHED_PARAMETER_NAME = @Value(published_parameter_name)
    READER_ENABLED = @Value(reader_enabled)
    WORKSPACE_ID = @Value(workspace_id)
    READER_FEATURE_TYPE_NAME = @Value(reader_feature_type_name)
    READER_KEYWORD = @Value(reader_keyword)
    PUBLISHED_PARAMETER_DEFAULT_VALUE = @Value(published_parameter_default_value)
    Output:Report -> Junction_2
    Output:Summary -> Junction
TransformerHistogram (reader FMW_1)
    attributes: workspace_id uint32, transformer_type string, transformer_count uint32
    -> BestPractice-TransformerAnalysis [Input:TransformerHistogram]
BestPractice-TransformerAnalysis
    TRANSFORMER_ENABLED = @Value(transformer_enabled)
    TRANSFORMER_TYPE = @Value(transformer_type)
    TRANSFORMER_NAME = @Value(transformer_name)
    TRANSFORMER_TYPE_2 = @Value(transformer_type)
    TRANSFORMER_ID = @Value(transformer_id)
    TRANSFORMER_COUNT = @Value(transformer_count)
    TRANSFORMER_PARAMETER_VALUE = @Value(transformer_parameter_value)
    TRANSFORMER_PARAMETER_NAME = @Value(transformer_parameter_name)
    CURRENT_TRANSFORMER_VERSION = @Value(current_transformer_version)
    MAX_TRANSFORMER_VERSION = @Value(max_transformer_version)
    Output:Summary -> Junction
    Output:Report -> Junction_2
Junction
    -> BestPractice-ReportSummary [Input:Summary]
BestPractice-ReportSummary
    READER_TYPE = @Value(reader_type)
    MAJORBUILDTEXT = @Value(MajorBuildText)
    READER_GENERATE_BUILD_NUMBER = @Value(reader_generate_build_number)
    EXCESSFTTEXT = @Value(ExcessFTText)
    DANGLINGREADERS = @Value(DanglingReaders)
    READER_ID = @Value(reader_id)
    HTML_CONTENT = @Value(html_content)
    READER_FEATURE_TYPE_ENABLED = @Value(reader_feature_type_enabled)
    MODBUILDLENGTH = @Value(ModBuildLength)
    FEATURE_TYPE_ID = @Value(feature_type_id)
    HISTORY = @Value(history)
    READER_FEATURE_TYPE_POSSIBLE_GEOMETRIES = @Value(reader_feature_type_possible_geometries)
    SUBORDER = @Value(SubOrder)
    MAJORBUILDID = @Value(MajorBuildID)
    CURRENTMAJORBUILD = @Value(CurrentMajorBuild)
    WORKSPACE_NAME_2 = @Value(workspace_name)
    FMEBUILDNUM = @Value(FMEBuildNum)
    USAGE = @Value(usage)
    REQUIREMENTS_FLAG = @Value(requirements_flag)
    CATEGORY = @Value(category)
    READER_FEATURE_TYPE_QUALIFIER = @Value(reader_feature_type_qualifier)
    READER_NAME = @Value(reader_name)
    ERRORMSG = @Value(ErrorMsg)
    SOURCE_DATASET = @Value(source_dataset)
    NUMFEATURETYPES = @Value(NumFeatureTypes)
    DANGLINGREADERTEXT = @Value(DanglingReaderText)
    READER_ENABLED = @Value(reader_enabled)
    WORKSPACE_ID = @Value(workspace_id)
    MODIFIED_BUILD_NUMBER = @Value(modified_build_number)
    WARNMSG = @Value(WarnMsg)
    READER_FEATURE_TYPE_NAME = @Value(reader_feature_type_name)
    READER_KEYWORD = @Value(reader_keyword)
    REQUIREMENT = @Value(requirement)
    WKSPPROPERTIESTEXT = @Value(WkspPropertiesText)
    Output:Report -> Junction_2
Junction_2
    -> BestPractice-ReportCollation [Input:Report]
BestPractice-ReportCollation
    HTML_CONTENT = @Value(html_content)
    REPORTORDER = @Value(ReportOrder)
    -> HTML (writer HTML_1)
HTML (writer HTML_1)
    attributes: html_content buffer

Bookmark: Not Currently Used
Annotations (reader FMW_1)
    attributes: workspace_id uint32, annotation_id uint32, annotation string, annotation_type string
ReaderHistogram (reader FMW_1)
    attributes: workspace_id uint32, reader_type string, reader_count uint32
TransformerOutputPortAttributes (reader FMW_1)
    attributes: workspace_id uint32, transformer_output_port_id string, transformer_output_port_attribute_name string, transformer_output_port_attribute_constant_value string, transformer_output_port_attribute_enabled string
FeatureTypeFormatAttributes (reader FMW_1)
    attributes: workspace_id uint32, feature_type_id uint32, format_attribute_name string, format_attribute_type string
FeatureTypeParameters (reader FMW_1)
    attributes: workspace_id uint32, feature_type_id uint32, feature_type_parameter_name string, feature_type_parameter_value string
WriterHistogram (reader FMW_1)
    attributes: workspace_id uint32, writer_type string, writer_count uint32
Bookmarks (reader FMW_1)
    attributes: workspace_id uint32, bookmark_id uint32, bookmark_name string, bookmark_description string
TransformerOutputPorts (reader FMW_1)
    attributes: workspace_id uint32, transformer_id uint32, transformer_output_port_id string, transformer_output_port_name string
