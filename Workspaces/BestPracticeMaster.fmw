FME workspace BestPracticeMaster.fmw

Creator
    GEOMTYPE = Geometry Object
    NUM = 1
    CREATED -> AttributeCreator
Note: IN THE FUTURE: / - Fetch these from an external file. / - NB: There is also a copy of this in the NoFeaturesTester, because otherwise it wouldn't be available to transformers after that point.
Note: We want to make sure that passes are listed as well as fails. So each test has an INFORM when it is good
Note: Localization. / Set text for Error, Warning, Information
AttributeCreator
    ATTR_TABLE:
      SET_TO bestpractices.text.error (buffer) = Error
      SET_TO bestpractices.text.warning (buffer) = Warning
      SET_TO bestpractices.text.information (buffer) = Information
    -> FeatureReader [INITIATOR]
Note: IN THE FUTURE: / - Allow setting test parameters via published parameters / - Allow picking which tests to carry out via pub params
FeatureReader
    ATTRIBUTES = Annotations,"workspace_id,custom_transformer_parent_name,annotation_id,annotation,annotation_type,fme_geometry{0}",Bookmarks,"workspace_id,custom_transformer_parent_name,bookmark_id,bookmark_name,bookmark_description,bookmark_contents,fme_geometry{0}",Breakpoints,"workspace_id,custom_transformer_parent_name,breakpoint_id,breakpoint_name,breakpoint_condition,breakpoint_test_clause,breakpoint_enabled,fme_geometry{0}",Connections,"workspace_id,custom_transformer_parent_name,connection_id,connection_source_id,connection_target_id,connection_source_port_desc,connection_target_port_desc,connection_enabled,connection_execution_index,connection_hidden,fme_geometry{0}",FeatureTypeFormatAttributes,"workspace_id,feature_type_id,format_attribute_name,format_attribute_type,fme_geometry{0}",FeatureTypeParameters,"workspace_id,feature_type_id,feature_type_parameter_name,feature_type_parameter_value,fme_geometry{0}",FeatureTypeUserAttributes,"workspace_id,feature_type_id,user_attribute_name,user_attribute_type,user_attribute_exposed,fme_geometry{0}",FileProperties,"workspace_id,file_path,file_size,creation_date,modified_date,last_run_date,password_protected,fme_geometry{0}",PublishedParameters,"workspace_id,custom_transformer_parent_name,published_parameter_name,published_parameter_type,published_parameter_default_value,published_parameter_containing_group,fme_geometry{0}",ReaderFeatureTypes,"workspace_id,reader_id,feature_type_id,reader_feature_type_qualifier,reader_feature_type_name,reader_feature_type_possible_geometries,reader_feature_type_enabled,fme_geometry{0}",ReaderHistogram,"workspace_id,reader_type,reader_count,fme_geometry{0}",ReaderParameters,"workspace_id,reader_id,reader_parameter_name,reader_parameter_value,fme_geometry{0}",Readers,"workspace_id,reader_id,reader_name,reader_keyword,reader_type,source_dataset,reader_enabled,reader_generate_build_number,fme_geometry{0}",Statistics,"workspace_id,num_published_parameters,num_annotations,num_bookmarks,num_breakpoints,num_readers,num_reader_feature_types,num_writers,num_writer_feature_types,num_transformers,num_custom_transformers,num_out_of_date_transformers,num_connections,fme_geometry{0}",TransformerHistogram,"workspace_id,transformer_type,transformer_count,fme_geometry{0}",TransformerOutputPortAttributes,"workspace_id,custom_transformer_parent_name,transformer_id,transformer_output_port_id,transformer_output_port_attribute_name,transformer_output_port_attribute_constant_value,transformer_output_port_attribute_enabled,fme_geometry{0}",TransformerOutputPorts,"workspace_id,custom_transformer_parent_name,transformer_id,transformer_output_port_id,transformer_output_port_name,fme_geometry{0}",TransformerParameters,"workspace_id,custom_transformer_parent_name,transformer_id,transformer_parameter_name,transformer_parameter_value,fme_geometry{0}",Transformers,"workspace_id,custom_transformer_parent_name,transformer_id,transformer_name,transformer_type,transformer_aliases,current_transformer_version,max_transformer_version,transformer_enabled,transformer_last_edit_build_number,transformer_order,custom_transformer_order,fme_geometry{0}",UserParameterStructures,"workspace_id,custom_transformer_parent_name,structure_definition,fme_geometry{0}",UserParameters,"workspace_id,custom_transformer_parent_name,user_parameter_name,user_parameter_definition,user_parameter_parent_group,user_parameter_default_value,fme_geometry{0}",WorkspaceProperties,"workspace_id,workspace_name,workspace_description,modified_build_number,category,help,history,requirement,requirements_flag,legal,use_markdown,last_save_date,fme_geometry{0}",WriterFeatureTypes,"workspace_id,writer_id,feature_type_id,writer_feature_type_qualifier,writer_feature_type_name,writer_feature_type_possible_geometries,writer_feature_type_enabled,fme_geometry{0}",WriterHistogram,"workspace_id,writer_type,writer_count,fme_geometry{0}",WriterParameters,"workspace_id,writer_id,writer_parameter_name,writer_parameter_value,fme_geometry{0}",Writers,"workspace_id,writer_id,writer_name,writer_keyword,writer_type,destination_dataset,writer_enabled,writer_generate_build_number,fme_geometry{0}"
    ATTR_ACCUM_MODE = Merge Initiator and Result
    ATTR_CONFLICT_RES = Use Result
    ATTR_IGNORE_NULLS = No
    COMBINE_GEOM = Use Result
    DATASET = C:\Users\MIreland\Documents\BlackHole\TestForBPAnalysis.fmw
    FMW_USE_UNIQUE_IDS = yes
    FMW_USE_UNIQUE_WORKSPACE_IDS = yes
    FORMAT = FMW
    ORDER_RESULTS = No
    OUTPUT_FEATURES_DISPLAY = Data Features
    Bookmarks -> BestPractice-Style [Input:Bookmarks]
    Breakpoints -> BestPractice-Debugging [Input:Breakpoints]
    Connections -> BestPractice-Debugging [Input:Connections]
    Connections -> BestPractice-CustomTransformers [Input:Connections]
    Statistics -> BestPractice-Style [Input:Statistics]
    TransformerOutputPorts -> BestPractice-CustomTransformers [Input:TransformersOutputPorts]
    TransformerParameters -> BestPractice-Performance [Input:TransformerParameters]
    TransformerParameters -> BestPractice-Parameters [Input:TransformerParameters]
    Transformers -> BestPractice-Debugging [Input:Transformers]
    Transformers -> BestPractice-Transformers [Input:Transformers]
    Transformers -> BestPractice-Performance [Input:Transformers]
    Transformers -> BestPractice-CustomTransformers [Input:Transformers]
    Transformers -> BestPractice-Style [Input:Transformers]
    UserParameters -> BestPractice-Parameters [Input:UserParameters]
    WorkspaceProperties -> BestPractice-Workspace [Input:WorkspaceProperties]
BestPractice-Style
    BESTPRACTICES.TEXT.ERROR = @Value(bestpractices.text.error)
    BESTPRACTICES.TEXT.INFORMATION = @Value(bestpractices.text.information)
    BESTPRACTICES.TEXT.WARNING = @Value(bestpractices.text.warning)
    BOOKMARK_CONTENTS = @Value(bookmark_contents)
    BOOKMARK_NAME = @Value(bookmark_name)
    FME_GEOMETRY_0_ = @Value(fme_geometry{0})
    NUM_ANNOTATIONS = @Value(num_annotations)
    NUM_BOOKMARKS = @Value(num_bookmarks)
    NUM_BREAKPOINTS = @Value(num_breakpoints)
    NUM_CONNECTIONS = @Value(num_connections)
    NUM_CUSTOM_TRANSFORMERS = @Value(num_custom_transformers)
    NUM_OUT_OF_DATE_TRANSFORMERS = @Value(num_out_of_date_transformers)
    NUM_PUBLISHED_PARAMETERS = @Value(num_published_parameters)
    NUM_READERS = @Value(num_readers)
    NUM_READER_FEATURE_TYPES = @Value(num_reader_feature_types)
    NUM_TRANSFORMERS = @Value(num_transformers)
    NUM_WRITERS = @Value(num_writers)
    NUM_WRITER_FEATURE_TYPES = @Value(num_writer_feature_types)
    TRANSFORMER_ID = @Value(transformer_id)
    TRANSFORMER_NAME = @Value(transformer_name)
    TRANSFORMER_TYPE = @Value(transformer_type)
    WORKSPACE_ID = @Value(workspace_id)
    -> Junction
BestPractice-Debugging
    BESTPRACTICES.TEXT.ERROR = @Value(bestpractices.text.error)
    BESTPRACTICES.TEXT.INFORMATION = @Value(bestpractices.text.information)
    BESTPRACTICES.TEXT.WARNING = @Value(bestpractices.text.warning)
    BREAKPOINT_CONDITION = @Value(breakpoint_condition)
    BREAKPOINT_ENABLED = @Value(breakpoint_enabled)
    BREAKPOINT_ID = @Value(breakpoint_id)
    BREAKPOINT_NAME = @Value(breakpoint_name)
    BREAKPOINT_TEST_CLAUSE = @Value(breakpoint_test_clause)
    CONNECTION_ENABLED = @Value(connection_enabled)
    CONNECTION_EXECUTION_INDEX = @Value(connection_execution_index)
    CONNECTION_HIDDEN = @Value(connection_hidden)
    CONNECTION_ID = @Value(connection_id)
    CONNECTION_SOURCE_ID = @Value(connection_source_id)
    CONNECTION_SOURCE_PORT_DESC = @Value(connection_source_port_desc)
    CONNECTION_TARGET_ID = @Value(connection_target_id)
    CONNECTION_TARGET_PORT_DESC = @Value(connection_target_port_desc)
    CUSTOM_TRANSFORMER_PARENT_NAME = @Value(custom_transformer_parent_name)
    FME_GEOMETRY_0_ = @Value(fme_geometry{0})
    NUM_CONNECTIONS = @Value(num_connections)
    TRANSFORMER_NAME = @Value(transformer_name)
    TRANSFORMER_TYPE = @Value(transformer_type)
    WORKSPACE_ID = @Value(workspace_id)
    -> Junction
BestPractice-Performance
    BESTPRACTICES.TEXT.ERROR = @Value(bestpractices.text.error)
    BESTPRACTICES.TEXT.INFORMATION = @Value(bestpractices.text.information)
    BESTPRACTICES.TEXT.WARNING = @Value(bestpractices.text.warning)
    TRANSFORMER_ID = @Value(transformer_id)
    TRANSFORMER_NAME = @Value(transformer_name)
    TRANSFORMER_PARAMETER_NAME = @Value(transformer_parameter_name)
    TRANSFORMER_PARAMETER_VALUE = @Value(transformer_parameter_value)
    TRANSFORMER_TYPE = @Value(transformer_type)
    -> Junction
BestPractice-Transformers
    BESTPRACTICES.TEXT.ERROR = @Value(bestpractices.text.error)
    BESTPRACTICES.TEXT.INFORMATION = @Value(bestpractices.text.information)
    BESTPRACTICES.TEXT.WARNING = @Value(bestpractices.text.warning)
    CURRENT_TRANSFORMER_VERSION = @Value(current_transformer_version)
    CUSTOM_TRANSFORMER_ORDER = @Value(custom_transformer_order)
    CUSTOM_TRANSFORMER_PARENT_NAME = @Value(custom_transformer_parent_name)
    FME_GEOMETRY_0_ = @Value(fme_geometry{0})
    MAX_TRANSFORMER_VERSION = @Value(max_transformer_version)
    NUM_OUT_OF_DATE_TRANSFORMERS = @Value(num_out_of_date_transformers)
    TRANSFORMER_ALIASES = @Value(transformer_aliases)
    TRANSFORMER_ENABLED = @Value(transformer_enabled)
    TRANSFORMER_ID = @Value(transformer_id)
    TRANSFORMER_LAST_EDIT_BUILD_NUMBER = @Value(transformer_last_edit_build_number)
    TRANSFORMER_NAME = @Value(transformer_name)
    TRANSFORMER_ORDER = @Value(transformer_order)
    TRANSFORMER_TYPE = @Value(transformer_type)
    WORKSPACE_ID = @Value(workspace_id)
    _CREATION_INSTANCE = @Value(_creation_instance)
    -> Junction
BestPractice-Parameters
    BESTPRACTICES.TEXT.ERROR = @Value(bestpractices.text.error)
    BESTPRACTICES.TEXT.INFORMATION = @Value(bestpractices.text.information)
    BESTPRACTICES.TEXT.WARNING = @Value(bestpractices.text.warning)
    CUSTOM_TRANSFORMER_PARENT_NAME = @Value(custom_transformer_parent_name)
    FME_GEOMETRY_0_ = @Value(fme_geometry{0})
    STRUCTURE_DEFINITION = @Value(structure_definition)
    TRANSFORMER_PARAMETER_NAME = @Value(transformer_parameter_name)
    TRANSFORMER_PARAMETER_VALUE = @Value(transformer_parameter_value)
    USER_PARAMETER_DEFINITION = @Value(user_parameter_definition)
    USER_PARAMETER_NAME = @Value(user_parameter_name)
    -> Junction
BestPractice-CustomTransformers
    BESTPRACTICES.TEXT.ERROR = @Value(bestpractices.text.error)
    BESTPRACTICES.TEXT.INFORMATION = @Value(bestpractices.text.information)
    BESTPRACTICES.TEXT.WARNING = @Value(bestpractices.text.warning)
    CONNECTION_SOURCE_ID = @Value(connection_source_id)
    CONNECTION_SOURCE_PORT_DESC = @Value(connection_source_port_desc)
    CUSTOM_TRANSFORMER_PARENT_NAME = @Value(custom_transformer_parent_name)
    FME_GEOMETRY_0_ = @Value(fme_geometry{0})
    TRANSFORMER_ID = @Value(transformer_id)
    TRANSFORMER_NAME = @Value(transformer_name)
    TRANSFORMER_OUTPUT_PORT_NAME = @Value(transformer_output_port_name)
    TRANSFORMER_TYPE = @Value(transformer_type)
    -> Junction
BestPractice-Workspace
    BESTPRACTICES.TEXT.ERROR = @Value(bestpractices.text.error)
    BESTPRACTICES.TEXT.INFORMATION = @Value(bestpractices.text.information)
    BESTPRACTICES.TEXT.WARNING = @Value(bestpractices.text.warning)
    CATEGORY = @Value(category)
    FME_GEOMETRY_0_ = @Value(fme_geometry{0})
    MODIFIED_BUILD_NUMBER = @Value(modified_build_number)
    WORKSPACE_DESCRIPTION = @Value(workspace_description)
    WORKSPACE_NAME_2 = @Value(workspace_name)
    -> Junction
Junction
    -> AttributeManager
AttributeManager
    ATTR_TABLE:
      SET_TO bestpractice.test.group (varchar(200)) = @SubstringRegularExpression(@Value(bestpractice.test.details),^[^.]+,0,0,0,caseSensitive=TRUE)
      SET_TO bestpractice.test.type (varchar(200)) = @SubstringRegularExpression(@Value(bestpractice.test.details),[^.]*$,0,0,0,caseSensitive=TRUE)
      SET_TO Lists (buffer) = Yes
    -> Sampler
Sampler
    GROUP_BY = bestpractice.test.group
    RATE = 1
    SAMPLE_MODE = No
    SAMPLE_TYPE_LONG = First N Features
    SAMPLED -> JSONTemplater [TESTGROUP]
    SAMPLED -> JSONTemplater [TESTS]
    SAMPLED -> JSONTemplater [LISTS]
    NOT_SAMPLED -> JSONTemplater [TESTS]
    NOT_SAMPLED -> JSONTemplater [LISTS]
Creator_2
    GEOMTYPE = Geometry Object
    NUM = 1
    CREATED -> JSONTemplater [ROOT]
JSONTemplater
    LISTS_QUERY_EXPR:
      {
          (: Check if there is info about a parent custom transformer :)
          if (fme:has-attribute("bestpractice.test.list{0}.custom_transformer_parent_name"))
          then
          {
              "Parent Custom Transformer": fme:get-list-attribute("bestpractice.test.list{}.custom_transformer_parent_name")
          }
          else
          {
              (:  :)
          }
      },

      {
          (: Check if there is info about transformers :)
          if (fme:has-attribute("bestpractice.test.list{0}.transformer_name"))
          then
          {
              "Transformer Names": fme:get-list-attribute("bestpractice.test.list{}.transformer_name")
          }
          else
          {
              (:  :)
          }
      },

      {
          (: Check if there is info about transformers :)
          if (fme:has-attribute("bestpractice.test.list{0}.transformer_type"))
          then
          {
              "Transformer Types": fme:get-list-attribute("bestpractice.test.list{}.transformer_type")
          }
          else
          {
              (:  :)
          }
      },

      {
          (: Check if there is info about transformers :)
          if (fme:has-attribute("bestpractice.test.list{0}.transformer_parameter_name"))
          then
          {
              "Transformer Parameter Names": fme:get-list-attribute("bestpractice.test.list{}.transformer_parameter_name")
          }
          else
          {
              (:  :)
          }
      },

      {
          (: Check if there is info about transformers :)
          if (fme:has-attribute("bestpractice.test.list{0}.transformer_parameter_value"))
          then
          {
              "Transformer Parameter Values": fme:get-list-attribute("bestpractice.test.list{}.transformer_parameter_value")
          }
          else
          {
              (:  :)
          }
      },

      {
          (: Check if there is info about parameters :)
          if (fme:has-attribute("bestpractice.test.list{0}.user_parameter_name"))
          then
          {
              "Parameter Name": fme:get-list-attribute("bestpractice.test.list{}.user_parameter_name")
          }
          else
          {
              (:  :)
          }
      },

      {
          (: Check if there is info about parameters :)
          if (fme:has-attribute("bestpractice.test.list{0}.prompt"))
          then
          {
              "Parameter Prompt": fme:get-list-attribute("bestpractice.test.list{}.prompt")
          }
          else
          {
              (:  :)
          }
      },

      {
          (: Check if there is info about parameters :)
          if (fme:has-attribute("bestpractice.test.list{0}.promptStringLength"))
          then
          {
              "Prompt Length": fme:get-list-attribute("bestpractice.test.list{}.promptStringLength")
          }
          else
          {
              (:  :)
          }
      },

      {
          (: Check if there is info about bookmarks :)
          if (fme:has-attribute("bestpractice.test.list{0}.bookmark_name"))
          then
          {
              "Bookmark Name": fme:get-list-attribute("bestpractice.test.list{}.bookmark_name"),
              "Bookmark Object Count": fme:get-list-attribute("bestpractice.test.list{}.BookmarkObjectCount")
          }
          else
          {
              (:  :)
          }
      },

      {
          (: Check if there is info about breakpoints :)
          if (fme:has-attribute("bestpractice.test.list{0}.breakpoint_name"))
          then
          {
              "Breakpoint Name": fme:get-list-attribute("bestpractice.test.list{}.breakpoint_name"),
              "Breakpoint Enabled": fme:get-list-attribute("bestpractice.test.list{}.breakpoint_enabled")
          }
          else
          {
              (:  :)
          }
      }
    RESULT_ATTRIBUTE = _result
    ROOT_QUERY_EXPR:
      {|
          fme:process-features("TESTGROUP")
      |}
    TESTGROUP_QUERY_EXPR:
      {
          fme:get-attribute("bestpractice.test.group") : [
              fme:process-features("TESTS", "bestpractice.test.group", fme:get-attribute("bestpractice.test.group"))
          ]
      }
    TESTS_QUERY_EXPR:
      {
          "Test" : fme:get-attribute("bestpractice.test.type"),
          "Status" : fme:get-attribute("bestpractice.test.status"),
          "Statistic" : fme:get-attribute("bestpractice.test.statistic"),
          "Message" : fme:get-attribute("bestpractice.test.message")
      },

      {
          (: Check if there is info to follow :)
          if (fme:has-attribute("bestpractice.test.haslist"))
          then
      {
          "Information" : [
              fme:process-features("LISTS", "bestpractice.test.type", fme:get-attribute("bestpractice.test.type"))
          ]
      }
          else
          {
              (:  :)
          }
      }
    VISIBLE_QUERY_VALIDATE = Yes
    -> JSONFormatter
JSONFormatter
    ERROR_LIST_ATTR = _json_error
    FORMAT = Pretty Print
    INDENT_STYLE = 3 spaces
    JSON_DOCUMENT = @Value(_result)
    OUTPUT_ATTR = _formatted
    OUTPUT_ENCODING = UTF-8
    READ_FROM_FILE = NO
    REMOVE_EMPTY_OBJECTS_AND_ARRAYS = No
    REMOVE_EMPTY_STRINGS = No
    REMOVE_NULLS = No
    -> AttributeFileWriter
Note: Connection Info is "From ID" to "To ID". It needs to be converted to values to be useful.
AttributeFileWriter
    CHAR_ENCODING = utf-8
    FILE_NAME = C:\Users\MIreland\Documents\GitHub\BestPractice\ReportData.json
    OVERWRITE_FILE = Overwrite file
    SOURCE_ATTR = _formatted

Bookmark: GENERAL STATISTICS
Note: FUTURE / Workspace Name, Size / Number of R/W/Transformers, etc

FME custom transformer BestPractice-Parameters

Parameters:
- TRANSFORMER_PARAMETER_NAME = @Value(transformer_parameter_name)   # Transformer Parameter Name
- TRANSFORMER_PARAMETER_VALUE = @Value(transformer_parameter_value)   # Transformer Parameter Value
- STRUCTURE_DEFINITION = @Value(structure_definition)   # Structure Definition
- USER_PARAMETER_DEFINITION = @Value(user_parameter_definition)   # User Parameter Definition
- CUSTOM_TRANSFORMER_PARENT_NAME = @Value(custom_transformer_parent_name)   # Custom Transformer Parent Name
- FME_GEOMETRY_0_ = @Value(fme_geometry{0})   # Fme Geometry{0}
- USER_PARAMETER_NAME = @Value(user_parameter_name)   # User Parameter Name

Input:UserParameters (input)
    -> JSONFlattener
JSONFlattener
    ERROR_LIST_ATTR = _json_error
    JSON_DOCUMENT = @Value(user_parameter_definition)
    NEW_ATTRIBUTES = prompt type showArithmeticEditor required
    READ_FROM_FILE = NO
    RECURSIVE = Yes
    -> StringLengthCalculator
    -> TestFilter_2
    -> Junction_7
    -> TestFilter_5
    -> Junction_11
Junction_7
    -> Junction_9
    -> TestFilter_3
Junction_9
    -> TestFilter_4
TestFilter_4
    DEFAULT_VALUE = <UNFILTERED>
    PASSED_TEST_GROUP_OUTPUT = FIRST
    TEST_LIST:
      "BOOL_OP,OR,COMPOSITE_TEST,""""""1 OR 2"""""",TEST_CLAUSE,CASE_SENSITIVE_TEST @Value(prompt) = Enter Text Data
      CASE_SENSITIVE_TEST @Value(prompt) CONTAINS_REGEX ^Enter Text Data\s[\d]+$",Enter Text Data,"BOOL_OP,OR,COMPOSITE_TEST,""""""1 OR 2"""""",TEST_CLAUSE,CASE_SENSITIVE_TEST @Value(prompt) = Enter Numeric Data
      CASE_SENSITIVE_TEST @Value(prompt) CONTAINS_REGEX ^Enter Numeric Data\s[\d]+$",Enter Numeric Data,"BOOL_OP,OR,COMPOSITE_TEST,""""""1 OR 2"""""",TEST_CLAUSE,CASE_SENSITIVE_TEST @Value(prompt) = Select a Choice
      CASE_SENSITIVE_TEST @Value(prompt) CONTAINS_REGEX ^Select a Choice\s[\d]+$",Select a Choice,"BOOL_OP,OR,COMPOSITE_TEST,""""""1 OR 2"""""",TEST_CLAUSE,CASE_SENSITIVE_TEST @Value(prompt) = Select Yes/No
      CASE_SENSITIVE_TEST @Value(prompt) CONTAINS_REGEX ^Select Yes/No\s[\d]+$",Select Yes/No,"BOOL_OP,OR,COMPOSITE_TEST,""""""1 OR 2"""""",TEST_CLAUSE,CASE_SENSITIVE_TEST @Value(prompt) = Enter a Date
      CASE_SENSITIVE_TEST @Value(prompt) CONTAINS_REGEX ^Enter a Date\s[\d]+$",Enter a Date,"BOOL_OP,OR,COMPOSITE_TEST,""""""1 OR 2"""""",TEST_CLAUSE,CASE_SENSITIVE_TEST @Value(prompt) = Enter a Color
      CASE_SENSITIVE_TEST @Value(prompt) CONTAINS_REGEX ^Enter a Color\s[\d]+$",Enter a Color,"BOOL_OP,OR,COMPOSITE_TEST,""""""1 OR 2"""""",TEST_CLAUSE,CASE_SENSITIVE_TEST @Value(prompt) = Select a File
      CASE_SENSITIVE_TEST @Value(prompt) CONTAINS_REGEX ^Select a File\s[\d]+$",Select a File,"BOOL_OP,OR,COMPOSITE_TEST,""""""1 OR 2"""""",TEST_CLAUSE,CASE_SENSITIVE_TEST @Value(prompt) = Enter a Password
      CASE_SENSITIVE_TEST @Value(prompt) CONTAINS_REGEX ^Enter a Password\s[\d]+$",Enter a Password,"BOOL_OP,OR,COMPOSITE_TEST,""""""1 OR 2"""""",TEST_CLAUSE,CASE_SENSITIVE_TEST @Value(prompt) = Select an Attribute Name
      CASE_SENSITIVE_TEST @Value(prompt) CONTAINS_REGEX ^Select an Attribute Name\s[\d]+$",Select an Attribute Name,"BOOL_OP,OR,COMPOSITE_TEST,""""""1 OR 2"""""",TEST_CLAUSE,CASE_SENSITIVE_TEST @Value(prompt) = Select a Coordinate System
      CASE_SENSITIVE_TEST @Value(prompt) CONTAINS_REGEX ^Select a Coordinate System\s[\d]+$",Select a Coordinate System,"BOOL_OP,OR,COMPOSITE_TEST,""""""1 OR 2"""""",TEST_CLAUSE,CASE_SENSITIVE_TEST @Value(prompt) = Select a Database Connection
      CASE_SENSITIVE_TEST @Value(prompt) CONTAINS_REGEX ^Select a Database Connection\s[\d]+$",Select a Database Connection,"BOOL_OP,OR,COMPOSITE_TEST,""""""1 OR 2"""""",TEST_CLAUSE,CASE_SENSITIVE_TEST @Value(prompt) = Select Geometry
      CASE_SENSITIVE_TEST @Value(prompt) CONTAINS_REGEX ^Select Geometry\s[\d]+$",Select Geometry,"BOOL_OP,OR,COMPOSITE_TEST,""""""1 OR 2"""""",TEST_CLAUSE,CASE_SENSITIVE_TEST @Value(prompt) = Select a Web Connection
      CASE_SENSITIVE_TEST @Value(prompt) CONTAINS_REGEX ^Select a Web Connection\s[\d]+$",Select a Web Connection,"BOOL_OP,OR,COMPOSITE_TEST,""""""1 OR 2"""""",TEST_CLAUSE,CASE_SENSITIVE_TEST @Value(prompt) = Select a Reprojection
      CASE_SENSITIVE_TEST @Value(prompt) CONTAINS_REGEX ^Select a Reprojection\s[\d]+$",Select a Reprojection
    Enter Text Data -> Aggregator_7
    Enter Numeric Data -> Aggregator_7
    Select a Choice -> Aggregator_7
    Select Yes/No -> Aggregator_7
    Enter a Date -> Aggregator_7
    Enter a Color -> Aggregator_7
    Select a File -> Aggregator_7
    Enter a Password -> Aggregator_7
    Select an Attribute Name -> Aggregator_7
    Select a Coordinate System -> Aggregator_7
    Select a Database Connection -> Aggregator_7
    Select Geometry -> Aggregator_7
    Select a Web Connection -> Aggregator_7
    Select a Reprojection -> Aggregator_7
TestFilter_3
    DEFAULT_VALUE = <UNFILTERED>
    PASSED_TEST_GROUP_OUTPUT = FIRST
    TEST_LIST:
      "BOOL_OP,OR,COMPOSITE_TEST,""""""1 OR 2"""""",TEST_CLAUSE,CASE_SENSITIVE_TEST @Value(user_parameter_name) = PARAMETER
      CASE_SENSITIVE_TEST @Value(user_parameter_name) CONTAINS_REGEX ^PARAMETER_[\d]+$",PARAMETER Name
    PARAMETER Name -> Aggregator_6
TestFilter_2
    DEFAULT_VALUE = <UNFILTERED>
    PASSED_TEST_GROUP_OUTPUT = FIRST
    TEST_LIST = "BOOL_OP,OR,COMPOSITE_TEST,""""""1"""""",TEST_CLAUSE,CASE_SENSITIVE_TEST @Value(prompt) = @UpperCase(@Value(prompt))",All upper case,"BOOL_OP,OR,COMPOSITE_TEST,""""""1"""""",TEST_CLAUSE,CASE_SENSITIVE_TEST @Value(prompt) = @LowerCase(@Value(prompt))",All lower case
    All upper case -> Aggregator_5
    All lower case -> Aggregator_4
StringLengthCalculator
    LENGTH_ATTR = promptStringLength
    SRC_ATTR = prompt
    -> TestFilter
TestFilter
    DEFAULT_VALUE = <UNFILTERED>
    PASSED_TEST_GROUP_OUTPUT = FIRST
    TEST_LIST:
      "BOOL_OP,AND,COMPOSITE_TEST,""""""1 AND 2"""""",TEST_CLAUSE,TEST @Value(type) = message
      TEST @Value(promptStringLength) > 100",Long Message,"BOOL_OP,AND,COMPOSITE_TEST,""""""1"""""",TEST_CLAUSE,TEST @Value(type) = message",Other Messages,"BOOL_OP,OR,COMPOSITE_TEST,""""""1"""""",TEST_CLAUSE,TEST @Value(promptStringLength) >= 35",Long Prompt,"BOOL_OP,OR,COMPOSITE_TEST,""""""1"""""",TEST_CLAUSE,TEST @Value(promptStringLength) < 5",Short Prompt
    Long Message -> Aggregator_3
    Long Prompt -> Aggregator
    Short Prompt -> Aggregator_2
TestFilter_5
    DEFAULT_VALUE = <UNFILTERED>
    PASSED_TEST_GROUP_OUTPUT = FIRST
    TEST_LIST:
      "BOOL_OP,AND,COMPOSITE_TEST,""""""1 AND 2"""""",TEST_CLAUSE,TEST @Value(type) = text
      TEST @Value(showArithmeticEditor) = Yes",Text with Arithmetic Editor
    Text with Arithmetic Editor -> Aggregator_8
Junction_11
    -> FeatureMerger [REQUESTOR]
Input:TransformerParameters (input)
    -> FeatureMerger [SUPPLIER]
FeatureMerger
    ATTR_ACCUM_MODE = Merge Supplier
    ATTR_CONFLICT_RES = Use Requestor
    IGNORE_NULLS = No
    JOIN_KEYS = @Value(user_parameter_name) @Value(transformer_parameter_name) AUTO
    MERGE_TYPE = Attributes Only
    PROCESS_DUPS = NO
    REJECT_NULL_MISSING_KEYS = No
    SUPPLIERS_FIRST = No
    MERGED -> TestFilter_6
TestFilter_6
    DEFAULT_VALUE = <UNFILTERED>
    PASSED_TEST_GROUP_OUTPUT = FIRST
    TEST_LIST:
      "BOOL_OP,AND,COMPOSITE_TEST,""""""1 AND 2"""""",TEST_CLAUSE,TEST @Value(required) = Yes
      TEST transformer_parameter_value ATTRIBUTE_IS_EMPTY """,Empty Required Attribute
    Empty Required Attribute -> Aggregator_9
TestFilter_7
    DEFAULT_VALUE = <UNFILTERED>
    PASSED_TEST_GROUP_OUTPUT = FIRST
    TEST_LIST = "BOOL_OP,OR,COMPOSITE_TEST,""""""1"""""",TEST_CLAUSE,TEST @Value(bestpractice.test.status) = @Value(bestpractices.text.error)",Error,"BOOL_OP,OR,COMPOSITE_TEST,""""""1"""""",TEST_CLAUSE,TEST @Value(bestpractice.test.status) = @Value(bestpractices.text.warning)",Warning,"BOOL_OP,OR,COMPOSITE_TEST,""""""1"""""",TEST_CLAUSE,TEST @Value(bestpractice.test.status) = @Value(bestpractices.text.information)",Information
    Error -> Logger_22
    Warning -> Logger_20
    Information -> Logger_21
Logger_22
    LOG_FEATURE = NONE
    MAXFEATS = 20
    MESSAGE = @Value(bestpractice.test.status): @Value(bestpractice.test.message)
    SEVERITY = ERROR
    LOGGED -> BulkAttributeRemover_3
Logger_20
    LOG_FEATURE = NONE
    MAXFEATS = 20
    MESSAGE = @Value(bestpractice.test.status): @Value(bestpractice.test.message)
    SEVERITY = WARN
    LOGGED -> BulkAttributeRemover_3
Logger_21
    LOG_FEATURE = NONE
    MAXFEATS = 20
    MESSAGE = @Value(bestpractice.test.statistic): @Value(bestpractice.test.message)
    SEVERITY = INFO
    LOGGED -> BulkAttributeRemover_3
BulkAttributeRemover_3
    ATTR_EXP = ^(?!bestpractice.test).*
    -> AttributeRemover_4
AttributeRemover_4
    LIST_ATTRS = fme_geometry{}
    -> Output (output)
Output (output)

Bookmark: Parameters with default prompts ("Enter Text Data")
Aggregator_7
    ACCUM_ATTRS_NAME = Merge Incoming Attributes
    AGGREGATE_TYPE = Homogeneous Collection (If Possible)
    COUNT_ATTR = bestpractice.test.statistic
    LIST_ATTRS_TO_INCLUDE = custom_transformer_parent_name user_parameter_name prompt
    LIST_NAME = bestpractice.test.list
    MODE = Geometry - Assemble One Level
    SEP = ,
    AGGREGATE -> BestPractice-MessageLookup
    AGGREGATE -> BestPractice-NoFeaturesTester_8
BestPractice-MessageLookup
    MessageIDNumber = 24
    -> Message:24F
Message:24F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_8
BestPractice-NoFeaturesTester_8
    NoInput -> BestPractice-MessageLookup_2
BestPractice-MessageLookup_2
    MessageIDNumber = 24
    -> Message:24
Note: PASS
Message:24: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_8
Note: FAIL
Junction_8
    -> TestFilter_7

Bookmark: Parameters named PARAMETER, PARAMETER_2, PARAMETER_3
Aggregator_6
    ACCUM_ATTRS_NAME = Merge Incoming Attributes
    AGGREGATE_TYPE = Homogeneous Collection (If Possible)
    COUNT_ATTR = bestpractice.test.statistic
    LIST_ATTRS_TO_INCLUDE = custom_transformer_parent_name user_parameter_name
    LIST_NAME = bestpractice.test.list
    MODE = Geometry - Assemble One Level
    SEP = ,
    AGGREGATE -> BestPractice-MessageLookup_3
    AGGREGATE -> BestPractice-NoFeaturesTester_7
BestPractice-MessageLookup_3
    MessageIDNumber = 25
    -> Message:25F
Note: FAIL
Message:25F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_6
BestPractice-NoFeaturesTester_7
    NoInput -> BestPractice-MessageLookup_4
BestPractice-MessageLookup_4
    MessageIDNumber = 25
    -> Message:25
Note: PASS
Message:25: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_6
Junction_6
    -> TestFilter_7

Bookmark: all upper case Parameter Prompts
Aggregator_5
    ACCUM_ATTRS_NAME = Merge Incoming Attributes
    AGGREGATE_TYPE = Homogeneous Collection (If Possible)
    COUNT_ATTR = bestpractice.test.statistic
    LIST_ATTRS_TO_INCLUDE = custom_transformer_parent_name prompt user_parameter_name
    LIST_NAME = bestpractice.test.list
    MODE = Geometry - Assemble One Level
    SEP = ,
    AGGREGATE -> BestPractice-MessageLookup_5
    AGGREGATE -> BestPractice-NoFeaturesTester_6
BestPractice-MessageLookup_5
    MessageIDNumber = 21
    -> Message:21F
Note: FAIL
Message:21F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction
BestPractice-NoFeaturesTester_6
    NoInput -> BestPractice-MessageLookup_6
BestPractice-MessageLookup_6
    MessageIDNumber = 21
    -> Message:21
Note: PASS
Message:21: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction
Junction
    -> TestFilter_7

Bookmark: all lower case Parameter Prompts
Aggregator_4
    ACCUM_ATTRS_NAME = Merge Incoming Attributes
    AGGREGATE_TYPE = Homogeneous Collection (If Possible)
    COUNT_ATTR = bestpractice.test.statistic
    LIST_ATTRS_TO_INCLUDE = custom_transformer_parent_name prompt user_parameter_name
    LIST_NAME = bestpractice.test.list
    MODE = Geometry - Assemble One Level
    SEP = ,
    AGGREGATE -> BestPractice-MessageLookup_7
    AGGREGATE -> BestPractice-NoFeaturesTester_5
BestPractice-MessageLookup_7
    MessageIDNumber = 20
    -> Message:20F
Note: FAIL
Message:20F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_2
BestPractice-NoFeaturesTester_5
    NoInput -> BestPractice-MessageLookup_8
BestPractice-MessageLookup_8
    MessageIDNumber = 20
    -> Message:20
Note: PASS
Message:20: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_2
Junction_2
    -> TestFilter_7

Bookmark: Extra Long Messages
Aggregator_3
    ACCUM_ATTRS_NAME = Merge Incoming Attributes
    AGGREGATE_TYPE = Homogeneous Collection (If Possible)
    COUNT_ATTR = bestpractice.test.statistic
    LIST_ATTRS_TO_INCLUDE = custom_transformer_parent_name prompt promptStringLength user_parameter_name
    LIST_NAME = bestpractice.test.list
    MODE = Geometry - Assemble One Level
    SEP = ,
    AGGREGATE -> BestPractice-MessageLookup_9
    AGGREGATE -> BestPractice-NoFeaturesTester_4
BestPractice-MessageLookup_9
    MessageIDNumber = 19
    -> Message:19F
Note: FAIL
Message:19F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_3
BestPractice-NoFeaturesTester_4
    NoInput -> BestPractice-MessageLookup_10
BestPractice-MessageLookup_10
    MessageIDNumber = 19
    -> Message:19
Note: PASS
Message:19: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_3
Junction_3
    -> TestFilter_7

Bookmark: Extra Long Parameter Prompts
Aggregator
    ACCUM_ATTRS_NAME = Merge Incoming Attributes
    AGGREGATE_TYPE = Homogeneous Collection (If Possible)
    COUNT_ATTR = bestpractice.test.statistic
    LIST_ATTRS_TO_INCLUDE = custom_transformer_parent_name prompt promptStringLength user_parameter_name
    LIST_NAME = bestpractice.test.list
    MODE = Geometry - Assemble One Level
    SEP = ,
    AGGREGATE -> BestPractice-MessageLookup_11
    AGGREGATE -> BestPractice-NoFeaturesTester_3
BestPractice-MessageLookup_11
    MessageIDNumber = 17
    -> Message:17F
Note: FAIL
Message:17F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_4
BestPractice-NoFeaturesTester_3
    NoInput -> BestPractice-MessageLookup_12
BestPractice-MessageLookup_12
    MessageIDNumber = 17
    -> Message:17
Note: PASS
Message:17: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_4
Junction_4
    -> TestFilter_7

Bookmark: Extra Short Parameter Prompts
Aggregator_2
    ACCUM_ATTRS_NAME = Merge Incoming Attributes
    AGGREGATE_TYPE = Homogeneous Collection (If Possible)
    COUNT_ATTR = bestpractice.test.statistic
    LIST_ATTRS_TO_INCLUDE = custom_transformer_parent_name prompt promptStringLength user_parameter_name
    LIST_NAME = bestpractice.test.list
    MODE = Geometry - Assemble One Level
    SEP = ,
    AGGREGATE -> BestPractice-MessageLookup_13
    AGGREGATE -> BestPractice-NoFeaturesTester_2
BestPractice-MessageLookup_13
    MessageIDNumber = 18
    -> Message:18F
Message:18F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_5
BestPractice-NoFeaturesTester_2
    NoInput -> BestPractice-MessageLookup_14
BestPractice-MessageLookup_14
    MessageIDNumber = 18
    -> Message:18
Message:18: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_5
Note: FAIL
Note: PASS
Junction_5
    -> TestFilter_7

Bookmark: Text Parameter Showing Arithmetic Editor
Aggregator_8
    ACCUM_ATTRS_NAME = Merge Incoming Attributes
    AGGREGATE_TYPE = Homogeneous Collection (If Possible)
    COUNT_ATTR = bestpractice.test.statistic
    LIST_ATTRS_TO_INCLUDE = custom_transformer_parent_name user_parameter_name prompt
    LIST_NAME = bestpractice.test.list
    MODE = Geometry - Assemble One Level
    SEP = ,
    AGGREGATE -> BestPractice-MessageLookup_15
    AGGREGATE -> BestPractice-NoFeaturesTester_9
BestPractice-MessageLookup_15
    MessageIDNumber = 26
    -> Message:26F
Message:26F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_10
BestPractice-NoFeaturesTester_9
    NoInput -> BestPractice-MessageLookup_16
BestPractice-MessageLookup_16
    MessageIDNumber = 26
    -> Message:26
Message:26: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_10
Note: PASS
Note: FAIL
Junction_10
    -> TestFilter_7

Bookmark: Required parameter is unset
Aggregator_9
    ACCUM_ATTRS_NAME = Merge Incoming Attributes
    AGGREGATE_TYPE = Homogeneous Collection (If Possible)
    COUNT_ATTR = bestpractice.test.statistic
    LIST_ATTRS_TO_INCLUDE = custom_transformer_parent_name user_parameter_name prompt
    LIST_NAME = bestpractice.test.list
    MODE = Geometry - Assemble One Level
    SEP = ,
    AGGREGATE -> BestPractice-MessageLookup_17
    AGGREGATE -> BestPractice-NoFeaturesTester_10
BestPractice-MessageLookup_17
    MessageIDNumber = 27
    -> Message:27F
Message:27F: AttributeCreator
    ATTR_TABLE:
      SET_TO bestpractice.test.status (buffer) = @Value(bestpractices.text.error)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_12
BestPractice-NoFeaturesTester_10
    NoInput -> BestPractice-MessageLookup_18
BestPractice-MessageLookup_18
    MessageIDNumber = 27
    -> Message:27
Note: PASS
Message:27: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_12
Note: FAIL
Junction_12
    -> TestFilter_7

FME custom transformer BestPractice-Performance

Parameters:
- TRANSFORMER_ID = @Value(transformer_id)   # Transformer Id
- TRANSFORMER_TYPE = @Value(transformer_type)   # Transformer Type
- TRANSFORMER_PARAMETER_NAME = @Value(transformer_parameter_name)   # Transformer Parameter Name
- TRANSFORMER_PARAMETER_VALUE = @Value(transformer_parameter_value)   # Transformer Parameter Value
- TRANSFORMER_NAME = @Value(transformer_name)   # Transformer Name

Input:TransformerParameters (input)
    -> FeatureMerger [SUPPLIER]
Input:Transformers (input)
    -> FeatureMerger [REQUESTOR]
FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(transformer_id) @Value(transformer_id) AUTO
    LIST_NAME = TransParamList
    MERGE_TYPE = Attributes Only
    PROCESS_DUPS = YES
    REJECT_NULL_MISSING_KEYS = No
    SUPPLIERS_FIRST = No
    MERGED -> AttributeFilter
    MERGED -> ListExploder_2
    MERGED -> TestFilter_3
TestFilter_5
    DEFAULT_VALUE = <UNFILTERED>
    PASSED_TEST_GROUP_OUTPUT = FIRST
    TEST_LIST = "BOOL_OP,OR,COMPOSITE_TEST,""""""1"""""",TEST_CLAUSE,TEST @Value(bestpractice.test.status) = @Value(bestpractices.text.error)",Error,"BOOL_OP,OR,COMPOSITE_TEST,""""""1"""""",TEST_CLAUSE,TEST @Value(bestpractice.test.status) = @Value(bestpractices.text.warning)",Warning,"BOOL_OP,OR,COMPOSITE_TEST,""""""1"""""",TEST_CLAUSE,TEST @Value(bestpractice.test.status) = @Value(bestpractices.text.information)",Information
    Error -> Logger_4
    Warning -> Logger_2
    Information -> Logger_3
Logger_4
    LOG_FEATURE = NONE
    MAXFEATS = 20
    MESSAGE = @Value(bestpractice.test.status): @Value(bestpractice.test.message)
    SEVERITY = ERROR
    LOGGED -> BulkAttributeRemover_2
Logger_2
    LOG_FEATURE = NONE
    MAXFEATS = 20
    MESSAGE = @Value(bestpractice.test.status): @Value(bestpractice.test.message)
    SEVERITY = WARN
    LOGGED -> BulkAttributeRemover_2
Logger_3
    LOG_FEATURE = NONE
    MAXFEATS = 20
    MESSAGE = @Value(bestpractice.test.statistic): @Value(bestpractice.test.message)
    SEVERITY = INFO
    LOGGED -> BulkAttributeRemover_2
BulkAttributeRemover_2
    ATTR_EXP = ^(?!bestpractice.test).*
    -> AttributeRemover
AttributeRemover
    LIST_ATTRS = fme_geometry{}
    -> Output (output)
Output (output)

Bookmark: Across Output Ports
ListExploder_2
    ATTR_ACCUM_MODE = Merge List Attributes
    ATTR_CONFLICT_RES = Use List Attribute Values
    INDEX_ATTR = _element_index
    LIST_ATTR = TransParamList{}
    ELEMENTS -> TestFilter_2
TestFilter_2
    DEFAULT_VALUE = <UNFILTERED>
    PASSED_TEST_GROUP_OUTPUT = FIRST
    TEST_LIST:
      "BOOL_OP,COMPOSITE,COMPOSITE_TEST,""""""1 AND ( 2 OR 3 )"""""",TEST_CLAUSE,TEST @Value(transformer_parameter_name) = PRESERVE_FEATURE_ORDER
      TEST @Value(transformer_parameter_value) = Across Output Ports
      TEST @Value(transformer_parameter_value) = ACROSS_OUTPUT_PORTS",Across Output Ports Set
    Across Output Ports Set -> Aggregator_5
    Across Output Ports Set -> BestPractice-NoFeaturesTester
Note: FAIL
Aggregator_5
    ACCUM_ATTRS_NAME = Merge Incoming Attributes
    AGGREGATE_TYPE = Homogeneous Collection (If Possible)
    COUNT_ATTR = bestpractice.test.statistic
    LIST_ATTRS_TO_INCLUDE = transformer_id transformer_type transformer_name
    LIST_NAME = bestpractice.test.list
    MODE = Geometry - Assemble One Level
    SEP = ,
    AGGREGATE -> BestPractice-MessageLookup
BestPractice-MessageLookup
    MessageIDNumber = 15
    -> Message:15F
Message:15F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction
Note: PASS
BestPractice-NoFeaturesTester
    NoInput -> BestPractice-MessageLookup_2
BestPractice-MessageLookup_2
    MessageIDNumber = 15
    -> Message:15
Message:15: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction
Junction
    -> TestFilter_5

Bookmark: Unused Performance Parameters
Note: Transformers with an "X First" parameter
AttributeFilter
    ATTR_NAME = transformer_type
    ATTR_VALUES = Clipper,Displacer,FeatureMerger,NeighborFinder,PointOnAreaOverlayer,SpatialFilter,<Empty>,<Missing>,<Null>,<Unfiltered>
    Clipper -> ListExploder
    Displacer -> ListExploder
    FeatureMerger -> ListExploder
    NeighborFinder -> ListExploder
    PointOnAreaOverlayer -> ListExploder
    SpatialFilter -> ListExploder
ListExploder
    ATTR_ACCUM_MODE = Merge List Attributes
    ATTR_CONFLICT_RES = Use List Attribute Values
    INDEX_ATTR = _element_index
    LIST_ATTR = TransParamList{}
    ELEMENTS -> TestFilter
TestFilter
    DEFAULT_VALUE = <UNFILTERED>
    PASSED_TEST_GROUP_OUTPUT = FIRST
    TEST_LIST:
      "BOOL_OP,AND,COMPOSITE_TEST,""""""1 AND 2 AND 3"""""",TEST_CLAUSE,CASE_INSENSITIVE_TEST @Value(transformer_type) = Clipper
      CASE_INSENSITIVE_TEST @Value(transformer_parameter_name) = CLIPPERS_FIRST
      CASE_INSENSITIVE_TEST @Value(transformer_parameter_value) != Clippers First",ClipperXFirstNotSet,"BOOL_OP,AND,COMPOSITE_TEST,""""""1 AND 2 AND 3"""""",TEST_CLAUSE,CASE_INSENSITIVE_TEST @Value(transformer_type) = Displacer
      CASE_INSENSITIVE_TEST @Value(transformer_parameter_name) = BASE_TYPE
      CASE_INSENSITIVE_TEST @Value(transformer_parameter_value) != Bases First",DisplacerXFirstNotSet,"BOOL_OP,AND,COMPOSITE_TEST,""""""1 AND 2 AND 3"""""",TEST_CLAUSE,CASE_INSENSITIVE_TEST @Value(transformer_type) = FeatureMerger
      CASE_INSENSITIVE_TEST @Value(transformer_parameter_name) = SUPPLIERS_FIRST
      CASE_INSENSITIVE_TEST @Value(transformer_parameter_value) != Yes",FeatureMergerXFirstNotSet,"BOOL_OP,AND,COMPOSITE_TEST,""""""1 AND 2 AND 3"""""",TEST_CLAUSE,CASE_INSENSITIVE_TEST @Value(transformer_type) = NeighborFinder
      CASE_INSENSITIVE_TEST @Value(transformer_parameter_name) = CANDIDATES_FIRST
      CASE_INSENSITIVE_TEST @Value(transformer_parameter_value) != Yes",NeighborFinderXFirstNotSet,"BOOL_OP,AND,COMPOSITE_TEST,""""""1 AND 2 AND 3"""""",TEST_CLAUSE,CASE_INSENSITIVE_TEST @Value(transformer_type) = PointOnAreaOverlayer
      CASE_INSENSITIVE_TEST @Value(transformer_parameter_name) = POLYS_FIRST
      CASE_INSENSITIVE_TEST @Value(transformer_parameter_value) != YES",POAOXFirstNotSet,"BOOL_OP,AND,COMPOSITE_TEST,""""""1 AND 2 AND 3"""""",TEST_CLAUSE,CASE_INSENSITIVE_TEST @Value(transformer_type) = SpatialFilter
      CASE_INSENSITIVE_TEST @Value(transformer_parameter_name) = BASE_TYPE
      CASE_INSENSITIVE_TEST @Value(transformer_parameter_value) != Filters First",SpatialFilterXFirstNotSet
    ClipperXFirstNotSet -> Aggregator_2
    DisplacerXFirstNotSet -> Aggregator_2
    FeatureMergerXFirstNotSet -> Aggregator_2
    NeighborFinderXFirstNotSet -> Aggregator_2
    POAOXFirstNotSet -> Aggregator_2
    SpatialFilterXFirstNotSet -> Aggregator_2
Note: FAIL
Aggregator_2
    ACCUM_ATTRS_NAME = Merge Incoming Attributes
    AGGREGATE_TYPE = Homogeneous Collection (If Possible)
    COUNT_ATTR = bestpractice.test.statistic
    LIST_ATTRS_TO_INCLUDE = transformer_type transformer_name transformer_parameter_name transformer_parameter_value
    LIST_NAME = bestpractice.test.list
    MODE = Geometry - Assemble One Level
    SEP = ,
    AGGREGATE -> BestPractice-MessageLookup_3
    AGGREGATE -> BestPractice-NoFeaturesTester_2
BestPractice-MessageLookup_3
    MessageIDNumber = 16
    -> Message:16F
Message:16F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_2
Note: PASS
BestPractice-NoFeaturesTester_2
    NoInput -> BestPractice-MessageLookup_4
BestPractice-MessageLookup_4
    MessageIDNumber = 16
    -> Message:16
Message:16: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_2
Junction_2
    -> TestFilter_5

Bookmark: FeatureReader reading both Data AND Schema
TestFilter_3
    DEFAULT_VALUE = <UNFILTERED>
    PASSED_TEST_GROUP_OUTPUT = FIRST
    TEST_LIST = "BOOL_OP,OR,COMPOSITE_TEST,""""""1"""""",TEST_CLAUSE,TEST @Value(transformer_type) = FeatureReader",FeatureReader
    FeatureReader -> ListSearcher
Note: FUTURE / Could check to see if SCHEMA and data ports are connected. If so, then we presume there is nothing to warn about.
ListSearcher
    ATTR_VALUE = OUTPUT_FEATURES_DISPLAY
    CASE = CASE_SENSITIVE
    INDEX_ATTR = _list_index
    LIST_ATTR = TransParamList{}.transformer_parameter_name
    MATCHTYPE = FIRST_MATCHED_ENCODED
    FOUND -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(transformer_parameter_value) = Schema and Data Features",Schema+Data
    Schema+Data -> Aggregator_3
Note: FAIL
Aggregator_3
    ACCUM_ATTRS_NAME = Merge Incoming Attributes
    AGGREGATE_TYPE = Homogeneous Collection (If Possible)
    COUNT_ATTR = bestpractice.test.statistic
    LIST_ATTRS_TO_INCLUDE = transformer_type transformer_name transformer_parameter_name transformer_parameter_value
    LIST_NAME = bestpractice.test.list
    MODE = Geometry - Assemble One Level
    SEP = ,
    AGGREGATE -> BestPractice-MessageLookup_5
    AGGREGATE -> BestPractice-NoFeaturesTester_3
BestPractice-MessageLookup_5
    MessageIDNumber = 37
    -> Message:37F
Message:37F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_3
Note: PASS
BestPractice-NoFeaturesTester_3
    NoInput -> BestPractice-MessageLookup_6
BestPractice-MessageLookup_6
    MessageIDNumber = 37
    -> Message:37
Message:37: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_3
Junction_3
    -> TestFilter_5

FME custom transformer BestPractice-Style

Parameters:
- FME_GEOMETRY_0_ = @Value(fme_geometry{0})   # Fme Geometry{0}
- NUM_ANNOTATIONS = @Value(num_annotations)   # Num Annotations
- NUM_BREAKPOINTS = @Value(num_breakpoints)   # Num Breakpoints
- NUM_CONNECTIONS = @Value(num_connections)   # Num Connections
- NUM_CUSTOM_TRANSFORMERS = @Value(num_custom_transformers)   # Num Custom Transformers
- NUM_OUT_OF_DATE_TRANSFORMERS = @Value(num_out_of_date_transformers)   # Num Out Of Date Transformers
- NUM_PUBLISHED_PARAMETERS = @Value(num_published_parameters)   # Num Published Parameters
- NUM_READER_FEATURE_TYPES = @Value(num_reader_feature_types)   # Num Reader Feature Types
- NUM_READERS = @Value(num_readers)   # Num Readers
- NUM_TRANSFORMERS = @Value(num_transformers)   # Num Transformers
- NUM_WRITER_FEATURE_TYPES = @Value(num_writer_feature_types)   # Num Writer Feature Types
- NUM_WRITERS = @Value(num_writers)   # Num Writers
- WORKSPACE_ID = @Value(workspace_id)   # Workspace Id
- NUM_BOOKMARKS = @Value(num_bookmarks)   # Num Bookmarks
- BOOKMARK_CONTENTS = @Value(bookmark_contents)   # Bookmark Contents
- TRANSFORMER_NAME = @Value(transformer_name)   # Transformer Name
- TRANSFORMER_ID = @Value(transformer_id)   # Transformer Id
- TRANSFORMER_TYPE = @Value(transformer_type)   # Transformer Type
- BOOKMARK_NAME = @Value(bookmark_name)   # Bookmark Name

Input:Statistics (input)
    -> TestFilter
Input:Bookmarks (input)
    -> AttributeSplitter
Note: Create a list of objects in the transformer.
AttributeSplitter
    ATTR_NAME = bookmark_contents
    DELIMITER = " "
    DROP_EMPTY_PARTS = Yes
    LIST_NAME = ObjectsList
    TRIM_OPTION = Both
    -> ListBasedFeatureMerger [REQUESTOR]
Input:Transformers (input)
    -> ListBasedFeatureMerger [SUPPLIER]
Note: Merge with the transformer list (because some objects are annotation, and we don't care about those).
ListBasedFeatureMerger
    ATTR_ACCUM_MODE = Merge Supplier
    ATTR_CONFLICT_RES = Use Requestor
    BUILD_INCOMPLETE = Merge Supplier Information
    IGNORE_NULLS = No
    LIST_ATTRS_TO_INCLUDE = transformer_name transformer_type
    LIST_NAME = ListThatAreTransformers
    MERGE_TYPE = Attributes Only
    MODE = NUM
    PROCESS_DUPS = Yes
    REFEEATTR = @Value(transformer_id)
    REFERATTR = ObjectsList{}
    MERGED -> ListElementCounter
    UNMERGED_REQUESTOR -> ListElementCounter
Note: Count transformers
Note: A bookmark is only merged if EVERY item in it is a transformer. Most are mixed, so are unmerged.
ListElementCounter
    CNT_ATTR = BookmarkObjectCount
    LIST_NAME = ListThatAreTransformers{}
    -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(BookmarkObjectCount) = 1",Too Few Objects,"BOOL_OP,OR,COMPOSITE_TEST,""""""1"""""",TEST_CLAUSE,TEST @Value(BookmarkObjectCount) > 10",Too Many Objects
    Too Few Objects -> Aggregator_5
    Too Many Objects -> Aggregator_2
Note: We have to split data like this (instead of using conditional values) because the Logger message type does not support conditional.
TestFilter_5
    DEFAULT_VALUE = <UNFILTERED>
    PASSED_TEST_GROUP_OUTPUT = FIRST
    TEST_LIST = "BOOL_OP,OR,COMPOSITE_TEST,""""""1"""""",TEST_CLAUSE,TEST @Value(bestpractice.test.status) = @Value(bestpractices.text.error)",Error,"BOOL_OP,OR,COMPOSITE_TEST,""""""1"""""",TEST_CLAUSE,TEST @Value(bestpractice.test.status) = @Value(bestpractices.text.warning)",Warning,"BOOL_OP,OR,COMPOSITE_TEST,""""""1"""""",TEST_CLAUSE,TEST @Value(bestpractice.test.status) = @Value(bestpractices.text.information)",Information
    Error -> Logger_14
    Warning -> Logger_12
    Information -> Logger_13
Logger_14
    LOG_FEATURE = NONE
    MAXFEATS = 20
    MESSAGE = @Value(bestpractice.test.status): @Value(bestpractice.test.message)
    SEVERITY = ERROR
    LOGGED -> AttributeRemover_3
Logger_12
    LOG_FEATURE = NONE
    MAXFEATS = 20
    MESSAGE = @Value(bestpractice.test.status): @Value(bestpractice.test.message)
    SEVERITY = WARN
    LOGGED -> AttributeRemover_3
Logger_13
    LOG_FEATURE = NONE
    MAXFEATS = 20
    MESSAGE = @Value(bestpractice.test.statistic): @Value(bestpractice.test.message)
    SEVERITY = INFO
    LOGGED -> AttributeRemover_3
AttributeRemover_3
    LIST_ATTRS = fme_geometry{}
    -> BulkAttributeRemover
BulkAttributeRemover
    ATTR_EXP = ^(?!bestpractice.test).*
    -> Output (output)
Output (output)

Bookmark: Style Statistical Analysis
Note: We don't need to use NoFeaturesTesters here because we are guaranteed a feature with the correct statistics attached.
Note: ALL Passing Ports
TestFilter
    DEFAULT_VALUE = <UNFILTERED>
    PASSED_TEST_GROUP_OUTPUT = ALL
    TEST_LIST = "BOOL_OP,OR,COMPOSITE_TEST,""""""1"""""",TEST_CLAUSE,TEST @Value(num_bookmarks) = 0",No Bookmarks,"BOOL_OP,OR,COMPOSITE_TEST,""""""1"""""",TEST_CLAUSE,TEST @Value(num_bookmarks) > 0",Bookmarks,"BOOL_OP,OR,COMPOSITE_TEST,""""""1"""""",TEST_CLAUSE,TEST @Value(num_annotations) = 0",No Annotation,"BOOL_OP,OR,COMPOSITE_TEST,""""""1"""""",TEST_CLAUSE,TEST @Value(num_annotations) > 0",Annotation
    No Bookmarks -> Junction
    Bookmarks -> AttributeCreator_2
    No Annotation -> Junction_2
    Annotation -> AttributeCreator_7
Junction
    -> BestPractice-MessageLookup
Note: Zero Bookmarks Test
BestPractice-MessageLookup
    MessageIDNumber = 5
    -> Message:05
Note: FAIL
Message:05: AttributeCreator
    ATTR_TABLE:
      SET_TO bestpractice.test.status (buffer) = @Value(bestpractices.text.error)
      SET_TO bestpractice.test.statistic (uint64) = 0
      SET_TO bestpractice.test.message (varchar(200)) = @ReplaceString(@Value(BestPractice-Plural-MSG),[VALUE],@Value(bestpractice.test.statistic),caseSensitive=TRUE)
    -> Junction_4
AttributeCreator_2
    ATTR_TABLE = SET_TO bestpractice.test.statistic (varchar(200)) = @Evaluate((@round((@Value(num_transformers)/@Value(num_bookmarks))*10))/10)
    -> TestFilter_2
Note: Bookmark Ratio Test / 0-5: Warn (too many bookmarks perhaps) / 5-10: Good / 10+: Warn (too few bookmarks perhaps)
TestFilter_2
    DEFAULT_VALUE = Adequate Bookmarks
    PASSED_TEST_GROUP_OUTPUT = FIRST
    TEST_LIST = "BOOL_OP,OR,COMPOSITE_TEST,""""""1"""""",TEST_CLAUSE,TEST @Value(bestpractice.test.statistic) < 5",Too Many Bookmarks,"BOOL_OP,OR,COMPOSITE_TEST,""""""1"""""",TEST_CLAUSE,TEST @Value(bestpractice.test.statistic) > 10",Too Few Bookmarks
    Too Many Bookmarks -> BestPractice-MessageLookup_2
    Too Few Bookmarks -> BestPractice-MessageLookup_3
    Adequate Bookmarks -> BestPractice-MessageLookup_4
BestPractice-MessageLookup_2
    MessageIDNumber = 6
    -> Message:06
Note: FAIL
Message:06: AttributeCreator
    ATTR_TABLE:
      SET_TO bestpractice.test.status (buffer) = @Value(bestpractices.text.warning)
      SET_TO bestpractice.test.message (varchar(200)) = @ReplaceString(@Value(BestPractice-Plural-MSG),[VALUE],@Value(bestpractice.test.statistic),caseSensitive=TRUE)
    -> Junction_4
BestPractice-MessageLookup_3
    MessageIDNumber = 7
    -> Message:07
Message:07: AttributeCreator
    ATTR_TABLE:
      SET_TO bestpractice.test.status (buffer) = @Value(bestpractices.text.warning)
      SET_TO bestpractice.test.message (varchar(200)) = @ReplaceString(@Value(BestPractice-Plural-MSG),[VALUE],@Value(bestpractice.test.statistic),caseSensitive=TRUE)
    -> Junction_4
BestPractice-MessageLookup_4
    MessageIDNumber = 8
    -> Message:08
Note: PASS
Message:08: AttributeCreator
    ATTR_TABLE:
      SET_TO bestpractice.test.status (buffer) = @Value(bestpractices.text.information)
      SET_TO bestpractice.test.message (varchar(200)) = @ReplaceString(@Value(BestPractice-Plural-MSG),[VALUE],@Value(bestpractice.test.statistic),caseSensitive=TRUE)
    -> Junction_4
Junction_2
    -> BestPractice-MessageLookup_5
BestPractice-MessageLookup_5
    MessageIDNumber = 9
    -> Message:09
Note: FAIL
Message:09: AttributeCreator
    ATTR_TABLE:
      SET_TO bestpractice.test.status (buffer) = @Value(bestpractices.text.error)
      SET_TO bestpractice.test.statistic (uint64) = 0
      SET_TO bestpractice.test.message (varchar(200)) = @ReplaceString(@Value(BestPractice-Plural-MSG),[VALUE],@Value(bestpractice.test.statistic),caseSensitive=TRUE)
    -> Junction_4
Note: Future: Allow ratios and tests to be set by published parameters (or similar). See Main canvas.
AttributeCreator_7
    ATTR_TABLE = SET_TO bestpractice.test.statistic (varchar(200)) = @Evaluate((@round((@Value(num_transformers)/@Value(num_annotations))*10))/10)
    -> TestFilter_3
Note: Annotation Ratio Test / 0-2: Warn (too much annotation perhaps) / 3-5: Good / 5+: Warn (too little annotation perhaps)
Note: Zero Annotation Test
TestFilter_3
    DEFAULT_VALUE = Adequate Annotations
    PASSED_TEST_GROUP_OUTPUT = FIRST
    TEST_LIST = "BOOL_OP,OR,COMPOSITE_TEST,""""""1"""""",TEST_CLAUSE,TEST @Value(bestpractice.test.statistic) < 2",Too Many Annotations,"BOOL_OP,OR,COMPOSITE_TEST,""""""1"""""",TEST_CLAUSE,TEST @Value(bestpractice.test.statistic) > 5",Too Few Annotations
    Too Many Annotations -> BestPractice-MessageLookup_6
    Too Few Annotations -> BestPractice-MessageLookup_7
    Adequate Annotations -> BestPractice-MessageLookup_8
BestPractice-MessageLookup_6
    MessageIDNumber = 10
    -> Message:10
Message:10: AttributeCreator
    ATTR_TABLE:
      SET_TO bestpractice.test.status (buffer) = @Value(bestpractices.text.warning)
      SET_TO bestpractice.test.message (varchar(200)) = @ReplaceString(@Value(BestPractice-Plural-MSG),[VALUE],@Value(bestpractice.test.statistic),caseSensitive=TRUE)
    -> Junction_4
BestPractice-MessageLookup_7
    MessageIDNumber = 11
    -> Message:11
Message:11: AttributeCreator
    ATTR_TABLE:
      SET_TO bestpractice.test.status (buffer) = @Value(bestpractices.text.warning)
      SET_TO bestpractice.test.message (varchar(200)) = @ReplaceString(@Value(BestPractice-Plural-MSG),[VALUE],@Value(bestpractice.test.statistic),caseSensitive=TRUE)
    -> Junction_4
BestPractice-MessageLookup_8
    MessageIDNumber = 12
    -> Message:12
Note: PASS
Message:12: AttributeCreator
    ATTR_TABLE:
      SET_TO bestpractice.test.status (buffer) = @Value(bestpractices.text.information)
      SET_TO bestpractice.test.message (varchar(200)) = @ReplaceString(@Value(BestPractice-Plural-MSG),[VALUE],@Value(bestpractice.test.statistic),caseSensitive=TRUE)
    -> Junction_4
Note: FAIL
Junction_4
    -> TestFilter_5

Bookmark: Bookmark with just 1 transformer
Aggregator_5
    ACCUM_ATTRS_NAME = Merge Incoming Attributes
    AGGREGATE_TYPE = Homogeneous Collection (If Possible)
    COUNT_ATTR = bestpractice.test.statistic
    LIST_ATTRS_TO_INCLUDE = BookmarkObjectCount bookmark_name
    LIST_NAME = bestpractice.test.list
    MODE = Geometry - Assemble One Level
    SEP = ,
    AGGREGATE -> BestPractice-MessageLookup_9
    AGGREGATE -> BestPractice-NoFeaturesTester_6
BestPractice-MessageLookup_9
    MessageIDNumber = 22
    -> Message:22F
Message:22F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_3
BestPractice-NoFeaturesTester_6
    NoInput -> BestPractice-MessageLookup_10
BestPractice-MessageLookup_10
    MessageIDNumber = 22
    -> Message:22
Message:22: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_3
Note: FAIL
Note: PASS
Junction_3
    -> TestFilter_5

Bookmark: Bookmark with >10 transformers
Aggregator_2
    ACCUM_ATTRS_NAME = Merge Incoming Attributes
    AGGREGATE_TYPE = Homogeneous Collection (If Possible)
    COUNT_ATTR = bestpractice.test.statistic
    LIST_ATTRS_TO_INCLUDE = BookmarkObjectCount bookmark_name
    LIST_NAME = bestpractice.test.list
    MODE = Geometry - Assemble One Level
    SEP = ,
    AGGREGATE -> BestPractice-MessageLookup_11
    AGGREGATE -> BestPractice-NoFeaturesTester_2
BestPractice-MessageLookup_11
    MessageIDNumber = 23
    -> Message:23F
Message:23F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_5
BestPractice-NoFeaturesTester_2
    NoInput -> BestPractice-MessageLookup_12
BestPractice-MessageLookup_12
    MessageIDNumber = 23
    -> Message:23
Message:23: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_5
Note: FAIL
Note: PASS
Junction_5
    -> TestFilter_5

FME custom transformer BestPractice-Workspace

Parameters:
- MODIFIED_BUILD_NUMBER = @Value(modified_build_number)   # Modified Build Number
- WORKSPACE_DESCRIPTION = @Value(workspace_description)   # Workspace Description
- WORKSPACE_NAME_2 = @Value(workspace_name)   # Workspace Name
- CATEGORY = @Value(category)   # category
- FME_GEOMETRY_0_ = @Value(fme_geometry{0})   # Fme Geometry{0}

Input:WorkspaceProperties (input)
    -> TestFilter_7
    -> HTTPCaller
TestFilter_5
    DEFAULT_VALUE = <UNFILTERED>
    PASSED_TEST_GROUP_OUTPUT = FIRST
    TEST_LIST = "BOOL_OP,OR,COMPOSITE_TEST,""""""1"""""",TEST_CLAUSE,TEST @Value(bestpractice.test.status) = @Value(bestpractices.text.error)",Error,"BOOL_OP,OR,COMPOSITE_TEST,""""""1"""""",TEST_CLAUSE,TEST @Value(bestpractice.test.status) = @Value(bestpractices.text.warning)",Warning,"BOOL_OP,OR,COMPOSITE_TEST,""""""1"""""",TEST_CLAUSE,TEST @Value(bestpractice.test.status) = @Value(bestpractices.text.information)",Information
    Error -> Logger_14
    Warning -> Logger_12
    Information -> Logger_13
Logger_14
    LOG_FEATURE = NONE
    MAXFEATS = 20
    MESSAGE = @Value(bestpractice.test.status): @Value(bestpractice.test.message)
    SEVERITY = ERROR
    LOGGED -> BulkAttributeRemover_3
Logger_12
    LOG_FEATURE = NONE
    MAXFEATS = 20
    MESSAGE = @Value(bestpractice.test.status): @Value(bestpractice.test.message)
    SEVERITY = WARN
    LOGGED -> BulkAttributeRemover_3
Logger_13
    LOG_FEATURE = NONE
    MAXFEATS = 20
    MESSAGE = @Value(bestpractice.test.statistic): @Value(bestpractice.test.message)
    SEVERITY = INFO
    LOGGED -> BulkAttributeRemover_3
BulkAttributeRemover_3
    ATTR_EXP = ^(?!bestpractice.test).*
    -> AttributeRemover_4
AttributeRemover_4
    LIST_ATTRS = fme_geometry{}
    -> Output (output)
Output (output)

Bookmark: No Workspace Name or Description is Set
Note: Sadly, there is no equivalent for custom transformer name/description
TestFilter_7
    DEFAULT_VALUE = <UNFILTERED>
    PASSED_TEST_GROUP_OUTPUT = ALL
    TEST_LIST = "BOOL_OP,OR,COMPOSITE_TEST,""""""1"""""",TEST_CLAUSE,TEST workspace_name NOT_ATTRIBUTE_HAS_A_VALUE """,No Name,"BOOL_OP,OR,COMPOSITE_TEST,""""""1"""""",TEST_CLAUSE,TEST workspace_description NOT_ATTRIBUTE_HAS_A_VALUE """,No Description,"BOOL_OP,OR,COMPOSITE_TEST,""""""1"""""",TEST_CLAUSE,TEST category NOT_ATTRIBUTE_HAS_A_VALUE """,No Category
    No Name -> BestPractice-MessageLookup_19
    No Description -> BestPractice-MessageLookup_20
    No Category -> BestPractice-MessageLookup_21
BestPractice-MessageLookup_19
    MessageIDNumber = 28
    -> Messages:28_29_2
Messages:28_29_2: AttributeCreator
    ATTR_TABLE:
      SET_TO bestpractice.test.status (buffer) = @Value(bestpractices.text.warning)
      SET_TO bestpractice.test.statistic (uint64) = 1
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
    -> Junction_2
BestPractice-MessageLookup_20
    MessageIDNumber = 29
    -> Messages:28_29_30
Messages:28_29_30: AttributeCreator
    ATTR_TABLE:
      SET_TO bestpractice.test.status (buffer) = @Value(bestpractices.text.warning)
      SET_TO bestpractice.test.statistic (uint64) = 1
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
    -> Junction_2
BestPractice-MessageLookup_21
    MessageIDNumber = 30
    -> Messages:28_29_3
Messages:28_29_3: AttributeCreator
    ATTR_TABLE:
      SET_TO bestpractice.test.status (buffer) = @Value(bestpractices.text.warning)
      SET_TO bestpractice.test.statistic (uint64) = 1
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
    -> Junction_2
Junction_2
    -> TestFilter_5

Bookmark: Get the Latest (Official) FME Build Number
HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://engage.safe.com/support/downloads/#official
    TRANSFER_TIMEOUT_LENGTH = 90
    USE_COOKIES = No
    VERIFY_SSL_CERTIFICATES = Yes
    -> StringSearcher
    <REJECTED> -> ParameterFetcher
StringSearcher
    CASE = no
    MATCHES_ATTR = BuildList
    REGEXP = Build \d{5}
    STRING_TO_SEARCH = @Value(_response_body)
    MATCHED -> ListDuplicateRemover
    NOT_MATCHED -> ParameterFetcher
ListDuplicateRemover
    SRC_LIST = BuildList{}.match
    -> ListSorter
Note: In my tests, the newest build was always first in the response, but I'll sort anyway just in case something changes.
ListSorter
    ORDER = Descending
    SRC_LIST = BuildList{}.match
    TYPE = Alphabetic
    -> ListIndexer
ListIndexer
    INDEX = 0
    LIST_ATTR = BuildList{}
    -> StringReplacer
StringReplacer
    CASE = NO
    FIND_TEXT = "Build "
    NO_MATCH = _FME_NO_OP_
    REGEXP = NO
    SRC_ATTRS = match
    -> AttributeRemover
Note: In the event that the Safe website doesn't give us what we want, let's use the local build number
ParameterFetcher
    ATTR_LIST = match $(FME_BUILD_NUM)
    -> AttributeRemover

Bookmark: Workspace vs Current Build and Version
AttributeRemover
    LIST_ATTRS = BuildList{}.match BuildList{}.startIndex
    -> AttributeManager
AttributeManager
    ATTR_TABLE:
      RENAME_SET_VALUE modified_build_number > UsedBuild (uint32)
      RENAME_SET_VALUE match > CurrentBuild (buffer)
      SET_TO CurrentVersion (varchar(200)) = @Left(@Value(CurrentBuild),2)
      SET_TO UsedVersion (varchar(200)) = @Left(@Value(UsedBuild),2)
    -> TestFilter
TestFilter
    DEFAULT_VALUE = <Unfiltered>
    PASSED_TEST_GROUP_OUTPUT = ALL
    TEST_LIST = "BOOL_OP,OR,COMPOSITE_TEST,""""""1"""""",TEST_CLAUSE,TEST @Value(UsedVersion) < @Value(CurrentVersion)",OlderVersion,"BOOL_OP,OR,COMPOSITE_TEST,""""""1"""""",TEST_CLAUSE,TEST @Value(UsedVersion) > @Value(CurrentVersion)",NewerVersion,"BOOL_OP,OR,COMPOSITE_TEST,""""""1"""""",TEST_CLAUSE,TEST @Value(UsedVersion) = @Value(CurrentVersion)",CurrentVersion,"BOOL_OP,OR,COMPOSITE_TEST,""""""1"""""",TEST_CLAUSE,TEST @Value(UsedBuild) < @Value(CurrentBuild)",OlderBuild,"BOOL_OP,OR,COMPOSITE_TEST,""""""1"""""",TEST_CLAUSE,TEST @Value(UsedBuild) > @Value(CurrentBuild)",NewerBuild,"BOOL_OP,OR,COMPOSITE_TEST,""""""1"""""",TEST_CLAUSE,TEST @Value(UsedBuild) = @Value(CurrentBuild)",CurrentBuild
    OlderVersion -> BestPractice-MessageLookup_2
    NewerVersion -> BestPractice-MessageLookup_3
    CurrentVersion -> BestPractice-MessageLookup_4
    OlderBuild -> BestPractice-MessageLookup_5
    NewerBuild -> BestPractice-MessageLookup_6
    CurrentBuild -> BestPractice-MessageLookup_7
BestPractice-MessageLookup_2
    MessageIDNumber = 31
    -> Message:31
Message:31: AttributeCreator
    ATTR_TABLE:
      SET_TO bestpractice.test.status (buffer) = @Value(bestpractices.text.error)
      SET_TO bestpractice.test.statistic (uint64) = 1
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
    -> Junction
BestPractice-MessageLookup_3
    MessageIDNumber = 32
    -> Message:32
Message:32: AttributeCreator
    ATTR_TABLE:
      SET_TO bestpractice.test.status (buffer) = @Value(bestpractices.text.error)
      SET_TO bestpractice.test.statistic (uint64) = 1
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
    -> Junction
BestPractice-MessageLookup_4
    MessageIDNumber = 33
    -> Message:33
Message:33: AttributeCreator
    ATTR_TABLE:
      SET_TO bestpractice.test.status (buffer) = @Value(bestpractices.text.information)
      SET_TO bestpractice.test.statistic (uint64) = 1
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
    -> Junction
BestPractice-MessageLookup_5
    MessageIDNumber = 34
    -> Message:31_2
Message:31_2: AttributeCreator
    ATTR_TABLE:
      SET_TO bestpractice.test.status (buffer) = @Value(bestpractices.text.warning)
      SET_TO bestpractice.test.statistic (uint64) = 1
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
    -> Junction
BestPractice-MessageLookup_6
    MessageIDNumber = 35
    -> Message:32_2
Message:32_2: AttributeCreator
    ATTR_TABLE:
      SET_TO bestpractice.test.status (buffer) = @Value(bestpractices.text.warning)
      SET_TO bestpractice.test.statistic (uint64) = 1
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
    -> Junction
BestPractice-MessageLookup_7
    MessageIDNumber = 36
    -> Message:33_2
Message:33_2: AttributeCreator
    ATTR_TABLE:
      SET_TO bestpractice.test.status (buffer) = @Value(bestpractices.text.information)
      SET_TO bestpractice.test.statistic (uint64) = 1
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
    -> Junction
Junction
    -> TestFilter_5

FME custom transformer BestPractice-Debugging

Parameters:
- FME_GEOMETRY_0_ = @Value(fme_geometry{0})   # Fme Geometry{0}
- CONNECTION_ENABLED = @Value(connection_enabled)   # Connection Enabled
- CONNECTION_EXECUTION_INDEX = @Value(connection_execution_index)   # Connection Execution Index
- CONNECTION_HIDDEN = @Value(connection_hidden)   # Connection Hidden
- CONNECTION_ID = @Value(connection_id)   # Connection Id
- CONNECTION_SOURCE_ID = @Value(connection_source_id)   # Connection Source Id
- CONNECTION_SOURCE_PORT_DESC = @Value(connection_source_port_desc)   # Connection Source Port Desc
- CONNECTION_TARGET_ID = @Value(connection_target_id)   # Connection Target Id
- CONNECTION_TARGET_PORT_DESC = @Value(connection_target_port_desc)   # Connection Target Port Desc
- NUM_CONNECTIONS = @Value(num_connections)   # Num Connections
- BREAKPOINT_ENABLED = @Value(breakpoint_enabled)   # Breakpoint Enabled
- BREAKPOINT_CONDITION = @Value(breakpoint_condition)   # Breakpoint Condition
- BREAKPOINT_ID = @Value(breakpoint_id)   # Breakpoint Id
- BREAKPOINT_NAME = @Value(breakpoint_name)   # Breakpoint Name
- BREAKPOINT_TEST_CLAUSE = @Value(breakpoint_test_clause)   # Breakpoint Test Clause
- CUSTOM_TRANSFORMER_PARENT_NAME = @Value(custom_transformer_parent_name)   # Custom Transformer Parent Name
- WORKSPACE_ID = @Value(workspace_id)   # Workspace Id
- TRANSFORMER_NAME = @Value(transformer_name)   # Transformer Name
- TRANSFORMER_TYPE = @Value(transformer_type)   # Transformer Type

Input:Connections (input)
    -> StatisticsCalculator
Note: Count Connections
StatisticsCalculator
    CALCULATION_MODE = LEXICAL
    FEAT_STATS = connection_enabled,LEXICAL,,,COUNT,<Unused>,<Unused>,,,,<Unused>,<Unused>,<Unused>,,
    COMPLETE -> AttributeRenamer
AttributeRenamer
    ATTR_TABLE = RENAME_SET_DEFAULT connection_enabled.total_count > num_connections
    MISSING_INPUT_ATTRS = REMOVE
    -> TestFilter
Input:Transformers (input)
    -> TestFilter_4
Input:Breakpoints (input)
    -> Aggregator_5
    -> BestPractice-NoFeaturesTester
TestFilter_5
    DEFAULT_VALUE = <UNFILTERED>
    PASSED_TEST_GROUP_OUTPUT = FIRST
    TEST_LIST = "BOOL_OP,OR,COMPOSITE_TEST,""""""1"""""",TEST_CLAUSE,TEST @Value(bestpractice.test.status) = @Value(bestpractices.text.error)",Error,"BOOL_OP,OR,COMPOSITE_TEST,""""""1"""""",TEST_CLAUSE,TEST @Value(bestpractice.test.status) = @Value(bestpractices.text.warning)",Warning,"BOOL_OP,OR,COMPOSITE_TEST,""""""1"""""",TEST_CLAUSE,TEST @Value(bestpractice.test.status) = @Value(bestpractices.text.information)",Information
    Error -> Logger_14
    Warning -> Logger_6
    Information -> Logger_7
Logger_14
    LOG_FEATURE = NONE
    MAXFEATS = 20
    MESSAGE = @Value(bestpractice.test.status): @Value(bestpractice.test.message)
    SEVERITY = ERROR
    LOGGED -> BulkAttributeRemover
Logger_6
    LOG_FEATURE = NONE
    MAXFEATS = 20
    MESSAGE = @Value(bestpractice.test.status): @Value(bestpractice.test.message)
    SEVERITY = WARN
    LOGGED -> BulkAttributeRemover
Logger_7
    LOG_FEATURE = NONE
    MAXFEATS = 20
    MESSAGE = @Value(bestpractice.test.statistic): @Value(bestpractice.test.message)
    SEVERITY = INFO
    LOGGED -> BulkAttributeRemover
BulkAttributeRemover
    ATTR_EXP = ^(?!bestpractice.test).*
    -> AttributeRemover_4
AttributeRemover_4
    LIST_ATTRS = fme_geometry{}
    -> Output (output)
Output (output)

Bookmark: Disabled Connections Analysis
TestFilter
    DEFAULT_VALUE = <UNFILTERED>
    PASSED_TEST_GROUP_OUTPUT = FIRST
    TEST_LIST = "BOOL_OP,OR,COMPOSITE_TEST,""""""1"""""",TEST_CLAUSE,TEST @Value(connection_enabled) = No",Disabled Connections
    Disabled Connections -> Aggregator
    Disabled Connections -> BestPractice-NoFeaturesTester_3
Aggregator
    ACCUM_ATTRS_NAME = Merge Incoming Attributes
    AGGREGATE_TYPE = Homogeneous Collection (If Possible)
    COUNT_ATTR = bestpractice.test.statistic
    LIST_ATTRS_TO_INCLUDE = connection_source_id connection_target_id
    LIST_NAME = bestpractice.test.list
    MODE = Geometry - Assemble One Level
    SEP = ,
    AGGREGATE -> BestPractice-MessageLookup_2
BestPractice-MessageLookup_2
    MessageIDNumber = 3
    -> Message:3F
Message:3F: AttributeCreator
    ATTR_TABLE:
      SET_TO bestpractice.test.status (buffer) = @Value(bestpractices.text.error)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Logger_12
Note: FAIL
Logger_12
    LOG_FEATURE = NONE
    MAXFEATS = 20
    MESSAGE = @Value(bestpractice.test.status): @Value(bestpractice.test.message)
    SEVERITY = ERROR
    LOGGED -> Junction
BestPractice-NoFeaturesTester_3
    NoInput -> BestPractice-MessageLookup
BestPractice-MessageLookup
    MessageIDNumber = 3
    -> Message:3
Message:3: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Logger_13
Note: PASS
Logger_13
    LOG_FEATURE = NONE
    MAXFEATS = 20
    MESSAGE = @Value(bestpractice.test.statistic): @Value(bestpractice.test.message)
    SEVERITY = ERROR
    LOGGED -> Junction
Junction
    -> TestFilter_5

Bookmark: Debugging Transformers
TestFilter_4
    DEFAULT_VALUE = <UNFILTERED>
    PASSED_TEST_GROUP_OUTPUT = FIRST
    TEST_LIST:
      "BOOL_OP,OR,COMPOSITE_TEST,""""""1 OR 2"""""",TEST_CLAUSE,TEST @Value(transformer_type) = Logger
      TEST @Value(transformer_type) = Inspector",DebuggingTransformers
    DebuggingTransformers -> Aggregator_3
    DebuggingTransformers -> BestPractice-NoFeaturesTester_2
Aggregator_3
    ACCUM_ATTRS_NAME = Merge Incoming Attributes
    AGGREGATE_TYPE = Homogeneous Collection (If Possible)
    COUNT_ATTR = bestpractice.test.statistic
    LIST_ATTRS_TO_INCLUDE = transformer_name transformer_type custom_transformer_parent_name
    LIST_NAME = bestpractice.test.list
    MODE = Geometry - Assemble One Level
    SEP = ,
    AGGREGATE -> BestPractice-MessageLookup_5
BestPractice-MessageLookup_5
    MessageIDNumber = 2
    -> Message:02F
Message:02F: AttributeCreator
    ATTR_TABLE:
      SET_TO bestpractice.test.status (buffer) = @Value(bestpractices.text.error)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Logger_4
Note: FAIL
Logger_4
    LOG_FEATURE = NONE
    MAXFEATS = 20
    MESSAGE = @Value(bestpractice.test.status): @Value(bestpractice.test.message)
    SEVERITY = ERROR
    LOGGED -> Junction_3
BestPractice-NoFeaturesTester_2
    NoInput -> BestPractice-MessageLookup_6
BestPractice-MessageLookup_6
    MessageIDNumber = 2
    -> Message:02
Message:02: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Logger_5
Note: PASS
Logger_5
    LOG_FEATURE = NONE
    MAXFEATS = 20
    MESSAGE = @Value(bestpractice.test.statistic): @Value(bestpractice.test.message)
    SEVERITY = INFO
    LOGGED -> Junction_3
Junction_3
    -> TestFilter_5

Bookmark: Breakpoints Statistical Analysis
Note: FAIL
Aggregator_5
    ACCUM_ATTRS_NAME = Merge Incoming Attributes
    AGGREGATE_TYPE = Homogeneous Collection (If Possible)
    COUNT_ATTR = bestpractice.test.statistic
    LIST_ATTRS_TO_INCLUDE = breakpoint_name breakpoint_enabled
    LIST_NAME = bestpractice.test.list
    MODE = Geometry - Assemble One Level
    SEP = ,
    AGGREGATE -> BestPractice-MessageLookup_3
BestPractice-MessageLookup_3
    MessageIDNumber = 4
    -> Message:4F
Message:4F: AttributeCreator
    ATTR_TABLE:
      SET_TO bestpractice.test.status (varchar(200)) = @Value(bestpractices.text.error)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Logger_2
Logger_2
    LOG_FEATURE = NONE
    MAXFEATS = 20
    MESSAGE = @Value(bestpractice.test.status): @Value(bestpractice.test.message)
    SEVERITY = ERROR
    LOGGED -> Junction_2
Note: PASS
BestPractice-NoFeaturesTester
    NoInput -> BestPractice-MessageLookup_4
BestPractice-MessageLookup_4
    MessageIDNumber = 4
    -> Message:4
Message:4: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Logger_3
Logger_3
    LOG_FEATURE = NONE
    MAXFEATS = 20
    MESSAGE = @Value(bestpractice.test.statistic): @Value(bestpractice.test.message)
    SEVERITY = INFO
    LOGGED -> Junction_2
Junction_2
    -> TestFilter_5

FME custom transformer BestPractice-CustomTransformers

Parameters:
- TRANSFORMER_ID = @Value(transformer_id)   # Transformer Id
- TRANSFORMER_OUTPUT_PORT_NAME = @Value(transformer_output_port_name)   # Transformer Output Port Name
- TRANSFORMER_NAME = @Value(transformer_name)   # Transformer Name
- CUSTOM_TRANSFORMER_PARENT_NAME = @Value(custom_transformer_parent_name)   # Custom Transformer Parent Name
- CONNECTION_SOURCE_ID = @Value(connection_source_id)   # Connection Source Id
- CONNECTION_SOURCE_PORT_DESC = @Value(connection_source_port_desc)   # Connection Source Port Desc
- FME_GEOMETRY_0_ = @Value(fme_geometry{0})   # Fme Geometry{0}
- TRANSFORMER_TYPE = @Value(transformer_type)   # Transformer Type

Input:Transformers (input)
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(transformer_type) = ExternalTransformer",Linked CT,"BOOL_OP,OR,COMPOSITE_TEST,""""""1"""""",TEST_CLAUSE,TEST @Value(transformer_type) = SubDocumentTransformer",Embedded CT,"BOOL_OP,OR,COMPOSITE_TEST,""""""1"""""",TEST_CLAUSE,TEST custom_transformer_parent_name ATTRIBUTE_HAS_A_VALUE """,Transformer in CT
    Linked CT -> FeatureMerger_3 [REQUESTOR]
    Embedded CT -> FeatureMerger_3 [REQUESTOR]
    Transformer in CT -> FeatureMerger [REQUESTOR]
Input:TransformersOutputPorts (input)
    -> TestFilter_2
    -> FeatureMerger_3 [SUPPLIER]
Input:Connections (input)
    -> StringReplacer
TestFilter_5
    DEFAULT_VALUE = <UNFILTERED>
    PASSED_TEST_GROUP_OUTPUT = FIRST
    TEST_LIST = "BOOL_OP,OR,COMPOSITE_TEST,""""""1"""""",TEST_CLAUSE,TEST @Value(bestpractice.test.status) = @Value(bestpractices.text.error)",Error,"BOOL_OP,OR,COMPOSITE_TEST,""""""1"""""",TEST_CLAUSE,TEST @Value(bestpractice.test.status) = @Value(bestpractices.text.warning)",Warning,"BOOL_OP,OR,COMPOSITE_TEST,""""""1"""""",TEST_CLAUSE,TEST @Value(bestpractice.test.status) = @Value(bestpractices.text.information)",Information
    Error -> Logger_14
    Warning -> Logger_12
    Information -> Logger_13
Logger_14
    LOG_FEATURE = NONE
    MAXFEATS = 20
    MESSAGE = @Value(bestpractice.test.status): @Value(bestpractice.test.message)
    SEVERITY = ERROR
    LOGGED -> BulkAttributeRemover_3
Logger_12
    LOG_FEATURE = NONE
    MAXFEATS = 20
    MESSAGE = @Value(bestpractice.test.status): @Value(bestpractice.test.message)
    SEVERITY = WARN
    LOGGED -> BulkAttributeRemover_3
Logger_13
    LOG_FEATURE = NONE
    MAXFEATS = 20
    MESSAGE = @Value(bestpractice.test.statistic): @Value(bestpractice.test.message)
    SEVERITY = INFO
    LOGGED -> BulkAttributeRemover_3
BulkAttributeRemover_3
    ATTR_EXP = ^(?!bestpractice.test).*
    -> AttributeRemover
AttributeRemover
    LIST_ATTRS = fme_geometry{}
    -> Output (output)
Output (output)

Bookmark: Custom Transformer Without its own Rejected Port
Note: Get Custom Transformer output ports
FeatureMerger_3
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(transformer_id) @Value(transformer_id) AUTO
    LIST_ATTRS_TO_INCLUDE = transformer_id transformer_output_port_name
    LIST_NAME = CustomTransformerListOfPorts
    MERGE_TYPE = Attributes Only
    PROCESS_DUPS = YES
    REJECT_NULL_MISSING_KEYS = No
    SUPPLIERS_FIRST = No
    MERGED -> ListExploder
ListExploder
    ATTR_ACCUM_MODE = Merge List Attributes
    ATTR_CONFLICT_RES = Use List Attribute Values
    INDEX_ATTR = _element_index
    LIST_ATTR = CustomTransformerListOfPorts{}
    ELEMENTS -> TestFilter_3
TestFilter_3
    DEFAULT_VALUE = <UNFILTERED>
    PASSED_TEST_GROUP_OUTPUT = FIRST
    TEST_LIST = "BOOL_OP,OR,COMPOSITE_TEST,""""""1"""""",TEST_CLAUSE,CASE_INSENSITIVE_TEST @Value(transformer_output_port_name) = <REJECTED>",RejectedPorts
    <UNFILTERED> -> DuplicateFilter
DuplicateFilter
    INPUT_ORDERED_CHOICE = No
    KEYATTR = transformer_id
    UNIQUE -> Aggregator_2
Aggregator_2
    ACCUM_ATTRS_NAME = Merge Incoming Attributes
    AGGREGATE_TYPE = Homogeneous Collection (If Possible)
    COUNT_ATTR = bestpractice.test.statistic
    LIST_ATTRS_TO_INCLUDE = transformer_type transformer_name custom_transformer_parent_name
    LIST_NAME = bestpractice.test.list
    MODE = Geometry - Assemble One Level
    SEP = ,
    AGGREGATE -> BestPractice-NoFeaturesTester_2
    AGGREGATE -> BestPractice-MessageLookup_2
Note: FAIL
BestPractice-MessageLookup_2
    MessageIDNumber = 14
    -> Message:14F
Message:14F: AttributeCreator
    ATTR_TABLE:
      SET_TO bestpractice.test.status (buffer) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> TestFilter_5
BestPractice-NoFeaturesTester_2
    NoInput -> BestPractice-MessageLookup_3
BestPractice-MessageLookup_3
    MessageIDNumber = 14
    -> Message:14
Note: PASS
Message:14: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> TestFilter_5

Bookmark: Unconnected Rejected Ports (INSIDE a Custom Transformer)
TestFilter_2
    DEFAULT_VALUE = <UNFILTERED>
    PASSED_TEST_GROUP_OUTPUT = FIRST
    TEST_LIST = "BOOL_OP,OR,COMPOSITE_TEST,""""""1"""""",TEST_CLAUSE,CASE_INSENSITIVE_TEST @Value(transformer_output_port_name) = <REJECTED>",RejectedPort
    RejectedPort -> FeatureMerger [SUPPLIER]
Note: Get Rejected ports
FeatureMerger
    ATTR_ACCUM_MODE = Merge Supplier
    ATTR_CONFLICT_RES = Use Requestor
    IGNORE_NULLS = No
    JOIN_KEYS = @Value(transformer_id) @Value(transformer_id) AUTO
    MERGE_TYPE = Attributes Only
    PROCESS_DUPS = NO
    REJECT_NULL_MISSING_KEYS = No
    SUPPLIERS_FIRST = No
    MERGED -> FeatureMerger_2 [REQUESTOR]
StringReplacer
    CASE = NO
    FIND_TEXT = <
    NO_MATCH = _FME_NO_OP_
    REGEXP = NO
    REPLACE_TEXT = <
    SRC_ATTRS = connection_source_port_desc
    -> StringReplacer_2
StringReplacer_2
    CASE = NO
    FIND_TEXT = >
    NO_MATCH = _FME_NO_OP_
    REGEXP = NO
    REPLACE_TEXT = >
    SRC_ATTRS = connection_source_port_desc
    -> FeatureMerger_2 [SUPPLIER]
Note: Get connections from those rejected ports
FeatureMerger_2
    ATTR_ACCUM_MODE = Merge Supplier
    ATTR_CONFLICT_RES = Use Requestor
    IGNORE_NULLS = No
    JOIN_KEYS = @Value(transformer_id) @Value(connection_source_id) AUTO @Value(transformer_output_port_name) @Value(connection_source_port_desc) AUTO
    MERGE_TYPE = Attributes Only
    PROCESS_DUPS = NO
    REJECT_NULL_MISSING_KEYS = No
    SUPPLIERS_FIRST = No
    UNMERGED_REQUESTOR -> Aggregator_5
    UNMERGED_REQUESTOR -> BestPractice-NoFeaturesTester
Note: If a transformer / ...is inside a CT / ...and it has an output port name <rejected> / ...and there is no connection source port for rejected / ...then that is an error.
Note: FAIL
Aggregator_5
    ACCUM_ATTRS_NAME = Merge Incoming Attributes
    AGGREGATE_TYPE = Homogeneous Collection (If Possible)
    COUNT_ATTR = bestpractice.test.statistic
    LIST_ATTRS_TO_INCLUDE = transformer_type transformer_name custom_transformer_parent_name
    LIST_NAME = bestpractice.test.list
    MODE = Geometry - Assemble One Level
    SEP = ,
    AGGREGATE -> BestPractice-MessageLookup_4
BestPractice-MessageLookup_4
    MessageIDNumber = 13
    -> Message:13F
Message:13F: AttributeCreator
    ATTR_TABLE:
      SET_TO bestpractice.test.status (buffer) = @Value(bestpractices.text.error)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> TestFilter_5
Note: PASS
BestPractice-NoFeaturesTester
    NoInput -> BestPractice-MessageLookup_5
BestPractice-MessageLookup_5
    MessageIDNumber = 13
    -> Message:13
Message:13: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> TestFilter_5

FME custom transformer BestPractice-Transformers

Parameters:
- NUM_OUT_OF_DATE_TRANSFORMERS = @Value(num_out_of_date_transformers)   # Num Out Of Date Transformers
- _CREATION_INSTANCE = @Value(_creation_instance)   # Creation Instance
- CURRENT_TRANSFORMER_VERSION = @Value(current_transformer_version)   # Current Transformer Version
- CUSTOM_TRANSFORMER_ORDER = @Value(custom_transformer_order)   # Custom Transformer Order
- CUSTOM_TRANSFORMER_PARENT_NAME = @Value(custom_transformer_parent_name)   # Custom Transformer Parent Name
- FME_GEOMETRY_0_ = @Value(fme_geometry{0})   # Fme Geometry{0}
- MAX_TRANSFORMER_VERSION = @Value(max_transformer_version)   # Max Transformer Version
- TRANSFORMER_ALIASES = @Value(transformer_aliases)   # Transformer Aliases
- TRANSFORMER_ENABLED = @Value(transformer_enabled)   # Transformer Enabled
- TRANSFORMER_ID = @Value(transformer_id)   # Transformer Id
- TRANSFORMER_LAST_EDIT_BUILD_NUMBER = @Value(transformer_last_edit_build_number)   # Transformer Last Edit Build Number
- TRANSFORMER_NAME = @Value(transformer_name)   # Transformer Name
- TRANSFORMER_ORDER = @Value(transformer_order)   # Transformer Order
- WORKSPACE_ID = @Value(workspace_id)   # Workspace Id
- TRANSFORMER_TYPE = @Value(transformer_type)   # Transformer Type

Input:Transformers (input)
    -> TestFilter_2
    -> TestFilter_3
TestFilter_5
    DEFAULT_VALUE = <UNFILTERED>
    PASSED_TEST_GROUP_OUTPUT = FIRST
    TEST_LIST = "BOOL_OP,OR,COMPOSITE_TEST,""""""1"""""",TEST_CLAUSE,TEST @Value(bestpractice.test.status) = @Value(bestpractices.text.error)",Error,"BOOL_OP,OR,COMPOSITE_TEST,""""""1"""""",TEST_CLAUSE,TEST @Value(bestpractice.test.status) = @Value(bestpractices.text.warning)",Warning,"BOOL_OP,OR,COMPOSITE_TEST,""""""1"""""",TEST_CLAUSE,TEST @Value(bestpractice.test.status) = @Value(bestpractices.text.information)",Information
    Error -> Logger_14
    Warning -> Logger_12
    Information -> Logger_13
Logger_14
    LOG_FEATURE = NONE
    MAXFEATS = 20
    MESSAGE = @Value(bestpractice.test.status): @Value(bestpractice.test.message)
    SEVERITY = ERROR
    LOGGED -> BulkAttributeRemover
Logger_12
    LOG_FEATURE = NONE
    MAXFEATS = 20
    MESSAGE = @Value(bestpractice.test.status): @Value(bestpractice.test.message)
    SEVERITY = WARN
    LOGGED -> BulkAttributeRemover
Logger_13
    LOG_FEATURE = NONE
    MAXFEATS = 20
    MESSAGE = @Value(bestpractice.test.statistic): @Value(bestpractice.test.message)
    SEVERITY = INFO
    LOGGED -> BulkAttributeRemover
BulkAttributeRemover
    ATTR_EXP = ^(?!bestpractice.test).*
    -> AttributeRemover_3
AttributeRemover_3
    LIST_ATTRS = fme_geometry{}
    -> Output (output)
Output (output)

Bookmark: Dubious Transformers
Note: Transformers like the FMEFunctionCaller, which really have no place in a well-designed workspace.
TestFilter_3
    DEFAULT_VALUE = <UNFILTERED>
    PASSED_TEST_GROUP_OUTPUT = FIRST
    TEST_LIST:
      "BOOL_OP,OR,COMPOSITE_TEST,""""""1 OR 2 OR 3 OR 4"""""",TEST_CLAUSE,TEST @Value(transformer_type) = FMEFunctionCaller
      TEST @Value(transformer_type) = FunctionCaller
      TEST @Value(transformer_type) = JavaScriptCaller
      TEST @Value(transformer_type) = SystemCaller",Dubious Transformers
    Dubious Transformers -> Aggregator_5
    Dubious Transformers -> BestPractice-NoFeaturesTester
Aggregator_5
    ACCUM_ATTRS_NAME = Merge Incoming Attributes
    AGGREGATE_TYPE = Homogeneous Collection (If Possible)
    COUNT_ATTR = bestpractice.test.statistic
    LIST_ATTRS_TO_INCLUDE = transformer_name transformer_type custom_transformer_parent_name
    LIST_NAME = bestpractice.test.list
    MODE = Geometry - Assemble One Level
    SEP = ,
    AGGREGATE -> BestPractice-MessageLookup_3
BestPractice-MessageLookup_3
    MessageIDNumber = 1
    -> Message:01F
Note: FAIL
Message:01F: AttributeCreator
    ATTR_TABLE:
      SET_TO bestpractice.test.status (buffer) = @Value(bestpractices.text.error)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_2
BestPractice-NoFeaturesTester
    NoInput -> BestPractice-MessageLookup_4
BestPractice-MessageLookup_4
    MessageIDNumber = 1
    -> Message:01
Note: PASS
Message:01: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_2
Junction_2
    -> TestFilter_5

Bookmark: Out of Date Transformers
Note: Some transformers don't have a max version and so can't be tested. I think they will be embedded CTs.
Note: Future: Do something different for transformers that are 2+ versions out of date (error, not warning)
TestFilter_2
    DEFAULT_VALUE = No Max Version
    PASSED_TEST_GROUP_OUTPUT = FIRST
    TEST_LIST = "BOOL_OP,OR,COMPOSITE_TEST,""""""1"""""",TEST_CLAUSE,TEST max_transformer_version ATTRIBUTE_HAS_A_VALUE """,Max Version OK
    Max Version OK -> ExpressionEvaluator
Note: Calculate versions out-of-date by / i.e. 1 version, 2 versions, 3, 4, etc
ExpressionEvaluator
    ACTION = Create New Attribute
    EXPRESSION = @Value(max_transformer_version)-@Value(current_transformer_version)
    VAL_ATTR = transformer_version_offset
    -> TestFilter
Note: Future: Calculate percentage of transformers that are out of date and error/warn/inform accordingly
TestFilter
    DEFAULT_VALUE = <UNFILTERED>
    PASSED_TEST_GROUP_OUTPUT = FIRST
    TEST_LIST = "BOOL_OP,OR,COMPOSITE_TEST,""""""1"""""",TEST_CLAUSE,TEST @Value(transformer_version_offset) > 0",Out of Date Transformers
    Out of Date Transformers -> Aggregator
    Out of Date Transformers -> BestPractice-NoFeaturesTester_2
Aggregator
    ACCUM_ATTRS_NAME = Merge Incoming Attributes
    AGGREGATE_TYPE = Homogeneous Collection (If Possible)
    COUNT_ATTR = bestpractice.test.statistic
    LIST_ATTRS_TO_INCLUDE = transformer_name transformer_type current_transformer_version max_transformer_version transformer_version_offset custom_transformer_parent_name
    LIST_NAME = bestpractice.test.list
    MODE = Geometry - Assemble One Level
    SEP = ,
    AGGREGATE -> BestPractice-MessageLookup_5
BestPractice-MessageLookup_5
    MessageIDNumber = 0
    -> Message:00F
Message:00F: AttributeCreator
    ATTR_TABLE:
      SET_TO bestpractice.test.status (varchar(200)) = @Value(bestpractices.text.warning)
      SET_TO bestpractice.test.message (varchar(200)) = FME_CONDITIONAL:DEFAULT_VALUE'@ReplaceString(@Value(BestPractice-Plural-MSG),[VALUE],@Value(bestpractice.test.statistic),caseSensitive=TRUE)'BOOL_OP;OR;COMPOSITE_TEST;1;TEST @Value(bestpractice.test.statistic) = 1'@ReplaceString(@Value(BestPractice-Singular-MSG),[VALUE],@Value(bestpractice.test.statistic),caseSensitive=TRUE)'FME_NUM_CONDITIONS2___
      SET_TO bestpractice.test.haslist (uint64) = 1
    -> Junction_3
BestPractice-NoFeaturesTester_2
    NoInput -> BestPractice-MessageLookup_6
BestPractice-MessageLookup_6
    MessageIDNumber = 0
    -> Message:00
Note: PASS
Message:00: AttributeCreator
    ATTR_TABLE:
      SET_TO bestpractice.test.status (buffer) = @Value(bestpractices.text.information)
      SET_TO bestpractice.test.statistic (uint64) = 0
      SET_TO bestpractice.test.message (varchar(200)) = @ReplaceString(@Value(BestPractice-Plural-MSG),[VALUE],@Value(bestpractice.test.statistic),caseSensitive=TRUE)
    -> Junction_3
Note: FAIL
Junction_3
    -> TestFilter_5
