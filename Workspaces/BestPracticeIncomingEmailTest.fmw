FME workspace BestPracticeIncomingEmailTest.fmw

Parameters:
- SourceDataset_TEXTLINE = C:\Users\imark\Documents\Black Hole\testemail.json   # Source Text File(s)

Readers:
- TEXTLINE_1: TEXTLINE from $(SourceDataset_TEXTLINE)

text_line (reader TEXTLINE_1)
    attributes: text_line_data buffer
    -> JSONFlattener
JSONFlattener
    RECURSIVE = Yes
    JSON_DOCUMENT = @Value(text_line_data)
    NEW_ATTRIBUTES = email_publisher_subject email_publisher_attachment{0}
    ERROR_LIST_ATTR = _json_error
    -> JSONFlattener_Output
JSONFlattener_Output: Logger
    MAXCOORDS = 20
    MESSAGE = Feature is:
    MAXFEATS = 20
