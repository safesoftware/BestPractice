FME workspace BestPracticeReportGenerator2017ForServer.fmw

Parameters:
- SourceDataset_TEXTLINE = C:\Users\imark\Documents\Black Hole\testemail.json   # Source Text File(s)
- DestDataset_TEXTLINE_4 = C:\FMEOutput\EmailOutput.txt   # Destination Text File

Readers:
- TEXTLINE_1: TEXTLINE from $(SourceDataset_TEXTLINE)

Writers:
- TEXTLINE_2: TEXTLINE to $(DestDataset_TEXTLINE_4)

Note: Get input from user email to Server
text_line (reader TEXTLINE_1)
    attributes: text_line_data buffer
    -> JSONFlattener
Note: Extract the attachment filename, and email details
JSONFlattener
    JSON_DOCUMENT = @Value(text_line_data)
    NEW_ATTRIBUTES = email_publisher_subject email_publisher_attachment{0} email_publisher_from email_publisher_to email_publisher_sent email_publisher_received
    ERROR_LIST_ATTR = _json_error
    RECURSIVE = Yes
    -> Tester
Note: Check there is an attachment
Tester
    BOOL_OP = OR
    TEST_CLAUSE = TEST @Value(email_publisher_attachment{0}) ATTRIBUTE_HAS_VALUE ""
    TEST_DESCRIPTION = ""
    TEST_MODE = Automatic
    PASSED -> FeatureReader [INITIATOR]
    FAILED -> AttributeManager_2
Note: Read the workspace from the attachment file
FeatureReader
    FORMAT = FMW
    DATASET = @Value(email_publisher_attachment{0})
    COMBINE_GEOM = Use Result
    ATTRIBUTES = Annotations,"workspace_id,annotation_id,annotation,annotation_type,fme_geometry{0}",Bookmarks,"workspace_id,bookmark_id,bookmark_name,bookmark_description,fme_geometry{0}",Breakpoints,"workspace_id,breakpoint_id,breakpoint_name,breakpoint_condition,breakpoint_test_clause,breakpoint_enabled,fme_geometry{0}",Connections,"connection_id,connection_source_id,connection_target_id,connection_source_port_desc,connection_target_port_desc,connection_enabled,connection_execution_index,connection_hidden,fme_geometry{0}",FeatureTypeFormatAttributes,"workspace_id,feature_type_id,format_attribute_name,format_attribute_type,fme_geometry{0}",FeatureTypeParameters,"workspace_id,feature_type_id,feature_type_parameter_name,feature_type_parameter_value,fme_geometry{0}",FeatureTypeUserAttributes,"workspace_id,feature_type_id,user_attribute_name,user_attribute_type,fme_geometry{0}",FileProperties,"workspace_id,file_path,file_size,creation_date,modified_date,last_run_date,fme_geometry{0}",PublishedParameters,"workspace_id,published_parameter_name,published_parameter_type,published_parameter_default_value,fme_geometry{0}",ReaderFeatureTypes,"workspace_id,reader_id,feature_type_id,reader_feature_type_qualifier,reader_feature_type_name,reader_feature_type_possible_geometries,reader_feature_type_enabled,fme_geometry{0}",ReaderHistogram,"workspace_id,reader_type,reader_count,fme_geometry{0}",ReaderParameters,"workspace_id,reader_id,reader_parameter_name,reader_parameter_value,fme_geometry{0}",Readers,"workspace_id,reader_id,reader_name,reader_keyword,reader_type,source_dataset,reader_enabled,reader_generate_build_number,fme_geometry{0}",Statistics,"workspace_id,num_published_parameters,num_annotations,num_bookmarks,num_breakpoints,num_readers,num_reader_feature_types,num_writers,num_writer_feature_types,num_transformers,num_custom_transformers,num_out_of_date_transformers,num_connections,fme_geometry{0}",TransformerHistogram,"workspace_id,transformer_type,transformer_count,fme_geometry{0}",TransformerOutputPortAttributes,"workspace_id,transformer_output_port_id,transformer_output_port_attribute_name,transformer_output_port_attribute_constant_value,transformer_output_port_attribute_enabled,fme_geometry{0}",TransformerOutputPorts,"workspace_id,transformer_id,transformer_output_port_id,transformer_output_port_name,fme_geometry{0}",TransformerParameters,"workspace_id,transformer_id,transformer_parameter_name,transformer_parameter_value,fme_geometry{0}",Transformers,"workspace_id,transformer_id,transformer_name,transformer_type,custom_transformer_parent_name,current_transformer_version,max_transformer_version,transformer_enabled,transformer_last_edit_build_number,fme_geometry{0}",WorkspaceProperties,"workspace_id,workspace_name,workspace_description,modified_build_number,category,usage,history,requirement,requirements_flag,legal,fme_geometry{0}",WriterFeatureTypes,"workspace_id,writer_id,feature_type_id,writer_feature_type_qualifier,writer_feature_type_name,writer_feature_type_possible_geometries,writer_feature_type_enabled,fme_geometry{0}",WriterHistogram,"workspace_id,writer_type,writer_count,fme_geometry{0}",WriterParameters,"workspace_id,writer_id,writer_parameter_name,writer_parameter_value,fme_geometry{0}",Writers,"workspace_id,writer_id,writer_name,writer_keyword,writer_type,destination_dataset,writer_enabled,writer_generate_build_number,fme_geometry{0}"
    OUTPUT_FEATURES_DISPLAY = Schema and Data Features
    ATTR_ACCUM_MODE = Merge Initiator and Result
    ATTR_CONFLICT_RES = Use Result
    Breakpoints -> BestPractice-FeatureInspectionAnalysis [Input:Breakpoints]
    Connections -> BestPractice-ReaderAnalysis [Input:Connections]
    FeatureTypeUserAttributes -> BestPractice:WriterAnalysis [Input:FeatureTypeUserAttributes]
    FileProperties -> FilenamePartExtractor
    PublishedParameters -> BestPractice-ReaderAnalysis [Input:PublishedParameters]
    PublishedParameters -> BestPractice:WriterAnalysis [Input:PublishedParameters]
    ReaderFeatureTypes -> BestPractice-ReaderAnalysis [Input:ReaderFeatureTypes]
    ReaderParameters -> BestPractice:WriterAnalysis [Input:ReaderParameters]
    Readers -> BestPractice-ReaderAnalysis [Input:Readers]
    Statistics -> BestPractice-StyleAnalysis [Input:Statistics]
    TransformerHistogram -> BestPractice-TransformerAnalysis [Input:TransformerHistogram]
    TransformerParameters -> BestPractice-TransformerAnalysis [Input:TransformerParameters]
    TransformerParameters -> BestPractice-PerformanceAnalysis [Input:TransformerParameters]
    Transformers -> BestPractice-TransformerAnalysis [Input:Transformers]
    Transformers -> BestPractice-PerformanceAnalysis [Input:Transformers]
    Transformers -> BestPractice:WriterAnalysis [Input:Transformers]
    WorkspaceProperties -> BestPractice-WorkspaceAnalysis [Input:WorkspaceProperties]
    WriterFeatureTypes -> BestPractice:WriterAnalysis [Input:WriterFeatureTypes]
    WriterParameters -> BestPractice:WriterAnalysis [Input:WriterParameters]
    Writers -> BestPractice:WriterAnalysis [Input:Writers]
FilenamePartExtractor
    SRC_ATTR = @Value(email_publisher_attachment{0})
    DIRPATH_ATTR = ReportWorkspacePath
    FULLNAME_ATTR = ReportWorkspaceName
    DIRNAME_ATTR = ReportWorkspaceFolder
    -> AttributeManager
Note: Create Report and File Names and Timestamp
AttributeManager
    ATTR_TABLE:
      RENAME_SET_VALUE file_size > ReportWorkspaceSize
      RENAME_SET_VALUE creation_date > ReportWorkspaceCreation
      RENAME_SET_VALUE modified_date > ReportWorkspaceModified
      RENAME_SET_VALUE last_run_date > ReportWorkspaceLastRun
      SET_TO ReportFileName = @Value(ReportWorkspaceName)-@DateTimeFormat(@DateTimeNow(),%Y%m%d%H%M%S)
      SET_TO ReportName = @Value(email_publisher_subject)
    -> AttributeFileReader
AttributeFileReader
    CHAR_ENCODING = utf-8
    FILE_NAME = @Value(email_publisher_attachment{0})
    DEST_ATTR = WorkspaceBeingAnalyzed
    -> BestPractice-ReportHeader
    -> Junction_3
BestPractice-ReportHeader
    REPORTWORKSPACEPATH = @Value(ReportWorkspacePath)
    REPORTWORKSPACECREATION = @Value(ReportWorkspaceCreation)
    REPORTWORKSPACEMODIFIED = @Value(ReportWorkspaceModified)
    REPORTWORKSPACEFOLDER = @Value(ReportWorkspaceFolder)
    REPORTWORKSPACELASTRUN = @Value(ReportWorkspaceLastRun)
    REPORTNAME = @Value(ReportName)
    REPORTWORKSPACE = @Value(ReportWorkspaceName)
    REPORTWORKSPACESIZE = @Value(ReportWorkspaceSize)
    Output:Report -> Junction_2
Note: Send email info to writer
Junction_3
    -> Junction_4
Note: Email Info
Junction_4
    -> FeatureMerger [SUPPLIER]
BestPractice-FeatureInspectionAnalysis: BestPractice-BreakpointAnalysis
    BREAKPOINT_NAME = @Value(breakpoint_name)
    BREAKPOINT_TEST_CLAUSE = @Value(breakpoint_test_clause)
    BREAKPOINT_ID = @Value(breakpoint_id)
    WORKSPACE_ID = @Value(workspace_id)
    BREAKPOINT_ENABLED = @Value(breakpoint_enabled)
    BREAKPOINT_CONDITION = @Value(breakpoint_condition)
    Output:Report -> Junction_2
    Output:Summary -> Junction
BestPractice-ReaderAnalysis
    READER_ID = @Value(reader_id)
    WORKSPACE_ID = @Value(workspace_id)
    READER_TYPE = @Value(reader_type)
    CONNECTION_SOURCE_PORT_DESC = @Value(connection_source_port_desc)
    READER_FEATURE_TYPE_NAME = @Value(reader_feature_type_name)
    PUBLISHED_PARAMETER_NAME = @Value(published_parameter_name)
    READER_FEATURE_TYPE_ENABLED = @Value(reader_feature_type_enabled)
    PUBLISHED_PARAMETER_DEFAULT_VALUE = @Value(published_parameter_default_value)
    READER_NAME = @Value(reader_name)
    PUBLISHED_PARAMETER_TYPE = @Value(published_parameter_type)
    READER_GENERATE_BUILD_NUMBER = @Value(reader_generate_build_number)
    READER_FEATURE_TYPE_POSSIBLE_GEOMETRIES = @Value(reader_feature_type_possible_geometries)
    READER_KEYWORD = @Value(reader_keyword)
    SOURCE_DATASET = @Value(source_dataset)
    READER_ENABLED = @Value(reader_enabled)
    READER_FEATURE_TYPE_QUALIFIER = @Value(reader_feature_type_qualifier)
    FEATURE_TYPE_ID = @Value(feature_type_id)
    Output:Report -> Junction_2
    Output:Summary -> Junction
BestPractice:WriterAnalysis
    WRITER_TYPE = @Value(writer_type)
    WORKSPACE_ID = @Value(workspace_id)
    WRITER_FEATURE_TYPE_POSSIBLE_GEOMETRIES = @Value(writer_feature_type_possible_geometries)
    USER_ATTRIBUTE_TYPE = @Value(user_attribute_type)
    USER_ATTRIBUTE_NAME = @Value(user_attribute_name)
    WRITER_ID = @Value(writer_id)
    DESTINATION_DATASET = @Value(destination_dataset)
    WRITER_PARAMETER_NAME = @Value(writer_parameter_name)
    PUBLISHED_PARAMETER_NAME = @Value(published_parameter_name)
    TRANSFORMER_TYPE = @Value(transformer_type)
    PUBLISHED_PARAMETER_DEFAULT_VALUE = @Value(published_parameter_default_value)
    WRITER_FEATURE_TYPE_QUALIFIER = @Value(writer_feature_type_qualifier)
    PUBLISHED_PARAMETER_TYPE = @Value(published_parameter_type)
    WRITER_GENERATE_BUILD_NUMBER = @Value(writer_generate_build_number)
    WRITER_KEYWORD = @Value(writer_keyword)
    READER_PARAMETER_NAME = @Value(reader_parameter_name)
    WRITER_NAME = @Value(writer_name)
    WRITER_FEATURE_TYPE_NAME = @Value(writer_feature_type_name)
    WRITER_PARAMETER_VALUE = @Value(writer_parameter_value)
    READER_PARAMETER_VALUE = @Value(reader_parameter_value)
    WRITER_FEATURE_TYPE_ENABLED = @Value(writer_feature_type_enabled)
    WRITER_ENABLED = @Value(writer_enabled)
    FEATURE_TYPE_ID = @Value(feature_type_id)
    Output:Report -> Junction_2
    Output:Summary -> Junction
BestPractice-PerformanceAnalysis
    TRANSFORMER_TYPE = @Value(transformer_type)
    MAX_TRANSFORMER_VERSION = @Value(max_transformer_version)
    CURRENT_TRANSFORMER_VERSION = @Value(current_transformer_version)
    TRANSFORMER_NAME = @Value(transformer_name)
    TRANSFORMER_ENABLED = @Value(transformer_enabled)
    WORKSPACE_ID = @Value(workspace_id)
    TRANSFORMER_LAST_EDIT_BUILD_NUMBER = @Value(transformer_last_edit_build_number)
    TRANSFORMER_PARAMETER_VALUE = @Value(transformer_parameter_value)
    TRANSFORMER_ID = @Value(transformer_id)
    TRANSFORMER_PARAMETER_NAME = @Value(transformer_parameter_name)
    Output:Report -> Junction_2
    Output:Summary -> Junction
BestPractice-TransformerAnalysis
    TRANSFORMER_TYPE = @Value(transformer_type)
    MAX_TRANSFORMER_VERSION = @Value(max_transformer_version)
    CURRENT_TRANSFORMER_VERSION = @Value(current_transformer_version)
    TRANSFORMER_TYPE_2 = @Value(transformer_type)
    TRANSFORMER_NAME = @Value(transformer_name)
    TRANSFORMER_ENABLED = @Value(transformer_enabled)
    TRANSFORMER_COUNT = @Value(transformer_count)
    TRANSFORMER_PARAMETER_VALUE = @Value(transformer_parameter_value)
    TRANSFORMER_ID = @Value(transformer_id)
    TRANSFORMER_PARAMETER_NAME = @Value(transformer_parameter_name)
    Output:Summary -> Junction
    Output:Report -> Junction_2
BestPractice-StyleAnalysis
    NUM_BREAKPOINTS = @Value(num_breakpoints)
    NUM_PUBLISHED_PARAMETERS = @Value(num_published_parameters)
    NUM_WRITERS = @Value(num_writers)
    NUM_CUSTOM_TRANSFORMERS = @Value(num_custom_transformers)
    NUM_ANNOTATIONS = @Value(num_annotations)
    NUM_READER_FEATURE_TYPES = @Value(num_reader_feature_types)
    WORKSPACE_ID = @Value(workspace_id)
    NUM_OUT_OF_DATE_TRANSFORMERS = @Value(num_out_of_date_transformers)
    NUM_READERS = @Value(num_readers)
    NUM_TRANSFORMERS = @Value(num_transformers)
    NUM_WRITER_FEATURE_TYPES = @Value(num_writer_feature_types)
    NUM_BOOKMARKS = @Value(num_bookmarks)
    Output:Summary -> Junction
    Output:Report -> Junction_2
BestPractice-WorkspaceAnalysis
    REQUIREMENT = @Value(requirement)
    MODIFIED_BUILD_NUMBER = @Value(modified_build_number)
    USAGE = @Value(usage)
    WORKSPACE_NAME_2 = @Value(workspace_name)
    HISTORY = @Value(history)
    WORKSPACE_ID = @Value(workspace_id)
    CATEGORY = @Value(category)
    REQUIREMENTS_FLAG = @Value(requirements_flag)
    Output:Report -> Junction_2
    Output:Summary -> Junction
Junction
    -> BestPractice-ReportSummary [Input:Summary]
BestPractice-ReportSummary
    READER_ID = @Value(reader_id)
    WORKSPACE_ID = @Value(workspace_id)
    READER_TYPE = @Value(reader_type)
    CURRENTMAJORBUILD = @Value(CurrentMajorBuild)
    NUMFEATURETYPES = @Value(NumFeatureTypes)
    SUBORDER = @Value(SubOrder)
    EXCESSFTTEXT = @Value(ExcessFTText)
    USAGE = @Value(usage)
    MAJORBUILDTEXT = @Value(MajorBuildText)
    DANGLINGREADERTEXT = @Value(DanglingReaderText)
    READER_FEATURE_TYPE_NAME = @Value(reader_feature_type_name)
    READER_FEATURE_TYPE_ENABLED = @Value(reader_feature_type_enabled)
    READER_NAME = @Value(reader_name)
    READER_GENERATE_BUILD_NUMBER = @Value(reader_generate_build_number)
    ERRORMSG = @Value(ErrorMsg)
    WARNMSG = @Value(WarnMsg)
    READER_KEYWORD = @Value(reader_keyword)
    READER_FEATURE_TYPE_POSSIBLE_GEOMETRIES = @Value(reader_feature_type_possible_geometries)
    REQUIREMENT = @Value(requirement)
    MAJORBUILDID = @Value(MajorBuildID)
    SOURCE_DATASET = @Value(source_dataset)
    FMEBUILDNUM = @Value(FMEBuildNum)
    MODBUILDLENGTH = @Value(ModBuildLength)
    WORKSPACE_NAME_2 = @Value(workspace_name)
    READER_ENABLED = @Value(reader_enabled)
    MODIFIED_BUILD_NUMBER = @Value(modified_build_number)
    DANGLINGREADERS = @Value(DanglingReaders)
    CATEGORY = @Value(category)
    REQUIREMENTS_FLAG = @Value(requirements_flag)
    HISTORY = @Value(history)
    FEATURE_TYPE_ID = @Value(feature_type_id)
    READER_FEATURE_TYPE_QUALIFIER = @Value(reader_feature_type_qualifier)
    WKSPPROPERTIESTEXT = @Value(WkspPropertiesText)
    HTML_CONTENT = @Value(html_content)
    Output:Report -> Junction_2
Junction_2
    -> BestPractice-ReportCollation [Input:Report]
BestPractice-ReportCollation
    REPORTORDER = @Value(ReportOrder)
    HTML_CONTENT = @Value(html_content)
    -> FeatureMerger [REQUESTOR]
Note: Retrieve Details of Incoming Email
FeatureMerger
    JOIN_KEYS = 1 1 AUTO
    REJECT_NULL_MISSING_KEYS = No
    PROCESS_DUPS = No
    IGNORE_NULLS = No
    SUPPLIERS_FIRST = No
    ATTR_ACCUM_MODE = Merge Supplier
    ATTR_CONFLICT_RES = Use Requestor
    MERGE_TYPE = Attributes Only
    MERGED -> FMEServerEmailGenerator
    MERGED -> FeatureWriter [HTML]
    MERGED -> AttributeCopier
Note: Write HTML Report
FeatureWriter
    DATASET = $(FME_SHAREDRESOURCE_DATA)\BestPractices\@Value(ReportFileName).html
    FORMAT = HTML
    FEATURE_TYPE_LIST_ATTR = _feature_type
    DATASET_ATTR = _dataset
    TOTAL_FEATURES_WRITTEN_ATTR = _total_features_written
AttributeCopier
    ATTR_TABLE = COPY WorkspaceBeingAnalyzed > text_line_data
    -> FeatureWriter_2 [text_line]
Note: Write Workspace
FeatureWriter_2
    FEATURE_TYPE_LIST_ATTR = _feature_type
    TEXTLINE_DESTINATION_DATASETTYPE_VALIDATION = Yes
    FORMAT = TEXTLINE
    TEXTLINE_WRITE_LAST_EOL = YES
    TOTAL_FEATURES_WRITTEN_ATTR = _total_features_written
    DATASET = $(FME_SHAREDRESOURCE_DATA)\BestPractices\@Value(ReportFileName).fmw
    TEXTLINE_MIME_TYPE = text/plain
    TEXTLINE_ENCODING = SYSTEM
    TEXTLINE_WRITE_UTF8_BOM = YES
    TEXTLINE_OVERWRITE_FILE = YES
    DATASET_ATTR = _dataset
    TEXTLINE_END_OF_LINE = System
Note: Create Report Name
AttributeManager_2
    ATTR_TABLE = SET_TO ReportName = @Value(email_publisher_subject)
    -> AttributeManager_3
Note: Generate Report Table
AttributeManager_3
    ATTR_TABLE:
      SET_TO ReportDateTime = @DateTimeFormat(@DateTimeNow(),%H:%M:%S UTC %d-%m-%Y)
      SET_TO ReportFileDetailsHTML = <table style="border: 1px solid black">
        <tr>
        <td style="border: 1px solid black; padding: 10px"><strong>Report Name</strong></td>
        <td style="border: 1px solid black; padding: 10px">@Value(ReportName)</td>
        </tr>
        <tr>
        <td style="border: 1px solid black; padding: 10px"><strong>Report Generated</strong></td>
        <td style="border: 1px solid black; padding: 10px">@Value(ReportDateTime)</td>
        </tr>
        <tr>
        <td style="border: 1px solid black; padding: 10px"><strong>Workspace Analyzed</strong></td>
        <td style="border: 1px solid black; padding: 10px">No workspace attached</td>
        </tr>
        </table>
    -> HTMLReportGenerator_2
Note: Create Report
HTMLReportGenerator_2
    GROUP_BY = email_publisher_from
    PAGE_CONFIG:
      HEADER{{TEXT;FME Workspace;HEADER;H1;ALIGNMENT;LEFT;COLOR;0,0,0;FME_CONTROLLER_QUERY_FILE;transformers\dependencies\html5\Header.fme}}HEADER{{TEXT; Best Practice Report;HEADER;H3;ALIGNMENT;LEFT;COLOR;0,0,0;FME_CONTROLLER_QUERY_FILE;transformers\dependencies\html5\Header.fme}}SEPARATOR{{WIDTH;1;FME_CONTROLLER_QUERY_FILE;transformers\dependencies\html5\Separator.fme}}HTML{{HTML;@Value(ReportFileDetailsHTML);FME_CONTROLLER_QUERY_FILE;transformers\dependencies\html5\Custom HTML.fme}}SEPARATOR{{WIDTH;1;FME_CONTROLLER_QUERY_FILE;transformers\dependencies\html5\Separator.fme}}HEADER{{TEXT;Reports List;HEADER;H3;ALIGNMENT;LEFT;COLOR;0,0,0;FME_CONTROLLER_QUERY_FILE;transformers\dependencies\html5\Header.fme}}HTML{{HTML;<h4> Report 1: HEADER </h4>

      <h5>Header 1: Title</h5>

      <h5>Header 2: General Information</h5>

      <ul>
      <li>Logs: Report name, Report datetime, Workspace name, File size, Creation datetime, Modified datetime, Last Run datetime</li>
      <li>Warnings about the limit of this procedure. </li>
      <li>Note current build number.</li>
      </ul>

      <hr>

      <h4> Report 2: WORKSPACE </h4>

      <h5>Workspace 1: Workspace Version</h5>

      <ul>
      <li>Test which version of FME the last edits were made in compared to the current FME version.</li>
      	<ul>
      	<li>If last edits are an older version, WARN about testing before deploying on the current version.</li>
      	<li>If last edits are a newer version, FAIL. Give an ERROR about using a beta build to construct a workspace.</li>
      	<li>If last edits are the same version, PASS.</li>
      	</ul>
      </ul>

      <h5>Workspace 2: Workspace Properties</h5>

      <ul>
      <li>Test for name and category being set.</li>
      	<ul>
      	<li>If one or the other are not set, WARN about this being bad for Best Practice.</li>
      	<li>If both are set, PASS.</li>
      	</ul>
      </ul>

      <hr>

      <h4> Report 3: STYLE </h4>

      <h5>Style 1: Bookmarks</h5>

      <ul>
      <li>Test for no bookmarks.</li>
      	<ul>
      	<li>If there are no bookmarks, FAIL. Give an ERROR about this being bad for Best Practice.</li>
      	</ul>
      <li>Calculate the number of transformers per bookmark.</li>
      	<ul>
      	<li>If there are too few bookmarks (>10 transformers per bookmark), WARN as being bad for Best Practice</li>
      	<li>If there are too many bookmarks (<5 transformers per bookmark), WARN as being bad for Best Practice</li>
      	<li>If there are an appropriate number of bookmarks, PASS.</li>
      	</ul>
      </ul>

      <h5>Style 2: Annotations</h5>

      <ul>
      <li>Test for no annotations.</li>
      	<ul>
      	<li>If there are no annotations, FAIL. Give an ERROR about this being bad for Best Practice.</li>
      	</ul>
      <ul>
      <li>Calculate the number of transformers per annotation.</li>
      	<ul>
      	<li>If there are too few annotations (>5 transformers per annotation), WARN as being bad for Best Practice</li>
      	<li>If there are too many annotations (<3 transformers per annotation), WARN as being bad for Best Practice</li>
      	<li>If there are an appropriate number of annotations, PASS.</li>
      	</ul>
      </ul>

      <hr>

      <h4> Report 4: BREAKPOINTS </h4>

      <h5>Breakpoints 1: Breakpoints</h5>

      <ul>
      <li>Check for breakpoints.</li>
      	<ul>
      	<li>If there are enabled breakpoints, FAIL. Give an ERROR about putting a workspace into production with these.</li>
      	<li>If there are disabled breakpoints, WARN about putting a workspace into production with these.</li>
      	<li>If there are no breakpoints, PASS.</li>
      	</ul>
      </ul>

      <hr>

      <h4> Report 5: READERS </h4>

      <h5>Readers 0: Zero Readers</h5>

      <ul>
      <li>Check for no Readers at all.</li>
      	<ul>
      	<li>If there are no readers, bypass other tests. Give a generic No Readers message.</li>
      	</ul>
      </ul>

      <h5>Readers 1: Build Number</h5>

      <ul>
      <li>Check each reader's "Generate Build" number against the current FME version.</li>
      	<ul>
      	<li>If the Generate Build was an older version, WARN suggesting upgrade before deploying on the current version.</li>
      	<li>If there are no older versions, PASS.</li>
      	</ul>
      </ul>

      <h5>Readers 2a: Disabled Readers</h5>

      <ul>
      <li>Check for disabled readers.</li>
      	<ul>
      	<li>If there are disabled readers, WARN that these are not useful when putting a workspace into production.</li>
      	<li>If there are no disabled readers, PASS.</li>
      	</ul>
      </ul>

      <h5>Readers 2b: Disabled Feature Types</h5>

      <ul>
      <li>Check for disabled feature types.</li>
      	<ul>
      	<li>If there are disabled feature types, WARN that these are not useful when putting a workspace into production.</li>
      	<li>If there are no disabled feature types, PASS.</li>
      	</ul>
      </ul>

      <h5>Readers 3: Dangling Readers</h5>

      <ul>
      <li>Check for dangling readers (those without a feature type).</li>
      	<ul>
      	<li>If there are dangling readers, FAIL. Give an ERROR that these are positively bad when putting a workspace into production.</li>
      	<li>If there are no dangling readers, PASS.</li>
      	</ul>
      </ul>

      <h5>Readers 4: Excess Feature Types</h5>

      <ul>
      <li>Check for a reader with >10 feature types.</li>
      	<ul>
      	<li>If there are readers with >10 feature types, WARN that this indicates the possible need for a merge filter.</li>
      	<li>If there are no readers with >10 feature types, PASS.</li>
      	</ul>
      </ul>

      <h5>Readers 5: Published Parameters</h5>

      <ul>
      <li>Check for basic reader parameters still published.</li>
      	<ul>
      	<li>If there are basic reader parameters still published, WARN that these might not be required.</li>
      	<li>If there are no basic reader parameters still published, PASS.</li>
      	</ul>
      </ul>

      <h5>Readers 6: Unconnected Feature Types</h5>

      <ul>
      <li>Check for reader feature types whose name is not a match in the connections list</li>
      	<ul>
      	<li>If there are feature types without a match, WARN that these could affect performance and should be removed</li>
      	<li>If there are no unconnected feature types, PASS.</li>
      	</ul>
      </ul>

      <hr>

      <h4> Report 6: WRITERS </h4>

      <h5>Writers 0: Zero Writers</h5>

      <ul>
      <li>Check for no Writers at all.</li>
      	<ul>
      	<li>If there are no writers, bypass other tests. Give a generic No Writers message.</li>
      	</ul>
      </ul>

      <h5>Writers 1: Build Number</h5>

      <ul>
      <li>Check each writer's "Generate Build" number against the current FME version.</li>
      	<ul>
      	<li>If the Generate Build was an older version, WARN suggesting upgrade before deploying on the current version.</li>
      	<li>If there are no older versions, PASS.</li>
      	</ul>
      </ul>

      <h5>Writers 2a: Disabled Writers</h5>

      <ul>
      <li>Check for disabled writers.</li>
      	<ul>
      	<li>If there are disabled writers, WARN that these are not useful when putting a workspace into production.</li>
      	<li>If there are no disabled writers, PASS.</li>
      	</ul>
      </ul>

      <h5>Writers 2b: Disabled Feature Types</h5>

      <ul>
      <li>Check for disabled feature types.</li>
      <ul>
      	<li>If there are disabled feature types, WARN that these are not useful when putting a workspace into production.</li>
      	<li>If there are no disabled feature types, PASS.</li>
      	</ul>
      </ul>

      <h5>Writers 3: Dangling Writers</h5>

      <ul>
      <li>Check for dangling writer (those without a feature type).</li>
      	<ul>
      	<li>If there are dangling writers, WARN that these are not useful when putting a workspace into production.</li>
      	<li>If there are no dangling writers, PASS.</li>
      	</ul>
      </ul>

      <h5>Writers 4: Invalid Feature Type Names</h5>

      <ul>
      <li>Check for writer feature type names with possibly invalid characters</li>
      	<ul>
      	<li>If there are characters outside of A-Z,a-z,0-9, WARN that these may be invalid (though FME should handle anyway).</li>
      	<li>If there are no characters outside of A-Z,a-z,0-9, PASS.</li>
      	</ul>
      </ul>

      <h5>Writers 5: Mixed Case Attr Names</h5>

      <ul>
      <li>Check Writer Attr Names for instances of mixed-case names (eg some UPPER, some lower, some MixedCase)</li>
      	<ul>
      	<li>If there are mixed-case names, WARN that this is not good practice.</li>
      	<li>If there are no mixed-case names, PASS. </li>
      	</ul>
      </ul>

      <h5>Writers 6: Coordinate Systems</h5>

      <ul>
      <li>Check for a writer setting a coordinate system.</li>
      <li>Check for a reader setting a coordinate system.</li>
      <li>Check for a CoordinateSystemSetter transformer.</li>
      	<ul>
      	<li>If a writer sets a coordinate system, and no reader sets it, and there is no CoordinateSystemSetter, WARN that FME needs to know what to reproject from</li>
      	<li>If there are no writers with coordinate systems, or there are but a reader/transformer sets it, PASS.</li>
      	</ul>
      </ul>

      <h5>Writers 7: Published Parameters</h5>

      <ul>
      <li>Check for basic writer parameters still published.</li>
      	<ul>
      	<li>If there are basic writer parameters still published, WARN that these might not be required.</li>
      	<li>If there are no basic writer parameters still published, PASS.</li>
      	</ul>
      </ul>

      <hr>

      <h4> Report 7: Transformers </h4>

      <h5>Transformers 1: Transformer Histogram</h5>

      <ul>
      <li>List the most-used transformers </li>
      </ul>

      <h5>Transformers 2: Percentage Check</h5>

      <ul>
      <li>Check percentage of overall count</li>
      	<ul>
      	<li>Check if there are 6 or more transformers (else the test is not worth doing)</li>
      	<li>If there are >5 transformers and >=25% are all the same type, WARN that this might not be a good scenario</li>
      	</ul>
      </ul>

      <h5>Transformers 3: Transformer Version</h5>

      <ul>
      <li>Check whether an update is required.</li>
      	<ul>
      	<li>If a transformer is not the latest version, WARN</li>
      	</ul>
      </ul>

      <h5>Transformers 4: Inspectors and Loggers</h5>

      <ul>
      <li>Check for Inspector transformers</li>
      	<ul>
      	<li>Enabled Inspectors = ERROR (note how bad this is for Server)</li>
      	<li>Disabled Inspectors = WARN</li>
      	</ul>
      <li>Check for Logger transformers</li>
      	<ul>
      	<li>Enabled Loggers = ERROR (note how bad this is for Server)</li>
      	<li>Disabled Loggers = WARNING</li>
      	</ul>
      </ul>

      <h5>Transformers 5: FMEFunctionCaller</h5>

      <ul>
      <li>Check for FMEFunctionCaller transformers</li>
      	<ul>
      	<li>If one exists, it indicates low-level badness. WARN (but a very strong one)</li>
      	</ul>
      </ul>

      <h5>Transformers 6: Similar Parameters</h5>

      <ul>
      <li>Check for transformer parameters that are the same value</li>
      	<ul>
      	<li>Suggest these might be better as a user parameter (possibly private) or Custom Transformer: WARN</li>
      	</ul>
      </ul>

      <hr>

      <h4> Report 8: PERFORMANCE </h4>

      <h5>Performance 0: Zero Transformers</h5>

      <ul>
      <li>Check for no transformers at all.</li>
      	<ul>
      	<li>If there are no transformers, bypass other transformer-related tests. Give a generic No Transformers message.</li>
      	</ul>
      </ul>

      <h5>Performance 1: Parallel Processing</h5>

      <ul>
      <li>Check parallel processing parameters for use of Aggressive or Extreme.</li>
      	<ul>
      	<li>If there are cases of Aggressive or Extreme, WARN that this may not guarantee good performance.</li>
      	<li>If there are no cases of Aggressive or Extreme, PASS.</li>
      	</ul>
      </ul>

      <h5>Performance 2: Parallel Processing 2</h5>

      <ul>
      <li>Check for multiple uses of Parallel Processing.</li>
      	<ul>
      	<li>If there are multiple uses, WARN that this may spawn too many processes.</li>
      	<li>If there are not multiple uses, PASS.</li>
      	</ul>
      </ul>

      <h5>Performance 3: Performance Parameters</h5>

      <ul>
      <li>Check for use of transformers with parameters for performance improvements (eg Clippers first)</li>
      <li>Tests for Clipper/Displacer/FeatureMerger/NeighborFinder/PointOnAreaOverlayer/SpatialFilter</li>
      	<ul>
      	<li>If such transformers exist, but don't use that parameter, WARN that this may impact performance.</li>
      	<li>If such transformers exist, and use that parameter, PASS.</li>
      	</ul>
      </ul>

      <hr>

      <h4> Report 9999: SUMMARY </h4>

      <h5>Summary 1</h5>

      <ul>
      <li>List the number of Errors</li>
      </ul>

      <h5>Summary 2</h5>

      <ul>
      <li>List the number of Warnings</li>
      </ul>
      </html>;FME_CONTROLLER_QUERY_FILE;transformers\dependencies\html5\Custom HTML.fme}}
    CONTENT_LIST = HEADER HEADER SEPARATOR HTML SEPARATOR HEADER HTML
    -> Junction_6
Note: Send Report
Junction_6
    -> Junction_5
Note: No Workspace Report / (List of Tests)
Junction_5
    -> FMEServerEmailGenerator
Note: Generate Outgoing Email
FMEServerEmailGenerator
    email_to = @Value(email_publisher_from)
    email_from = FMEBestPractice@gmail.com
    email_subject = FME Best Practice Analysis Results
    email_subscriber_content = @Value(html_content)
    -> text_line (writer TEXTLINE_2)
Note: Outgoing Email Writer
text_line (writer TEXTLINE_2)
    attributes: text_line_data buffer

FME custom transformer FMEServerEmailGenerator
This transformer provides an easy method for creating an email message to be sent by the FME Server Notification Service.
Input Ports
Input
This transformer will accept any feature.
Output Ports
Output
Features are output with text_line_data attribute required for the Text File Writer (see Usage Notes).
text_line_data: Contains JSON-formatted message that is required by the Email Subscription (see Usage Notes).
<Rejected>
Features will be rejected if the 'To:' field does not contain a valid email address in the form email@domain. Rejected features are output with value INVALID_PARAMETER stored in the fme_rejection_code attribute.
Parameters
To
Email address for To: field. 
Cc
Email address for Cc: field.
Bcc
Email address for Bcc: field.
From
Email address for From: field.
Reply to
Email address for Reply to: field.
Subject
Text string for subject of email.
Content
The main body of the email message.
Attachments
List of files to attach to email. For multiple files, separate filenames with a comma (e.g. file1.txt,file2.txt). File paths and features stored as attributes are both accepted.
Note: Attachments may not process if not accessible by FME Server.  
Usage Notes
Step 1. Create Topic and Email Subscription
In the FME Server Web UI, create a Topic for notifications to be sent to, and also create an Email Subscription that subscribes to this Topic.
Step 2. Create a Workspace
Once you fill out the the required paramerts for this transformer, you can send the email message in two different ways:
A. Send an email when the workspace completes:
- add a Text File Writer to the workspace
- connect FMEServerEmailGenerator Output to the Text File Writer
- publish the workspace
- register it with the Job Submitter, and/or Data Download, and/or Notification Service
- for each service, click the edit button
- expand the Notify on Job Completion section
- for Topics to Publish (Success), select the Topic created in Step 1
- for the Post Data parameter, select the Text File Writer added to the workspace
- finish publishing the workspace
- now the workspace will send an email whenever it is run through the FME Server Service you registered it with  
B. Send an email using a transformer:
- add an FMEServerNotifier transformer to your workflow
- configure it to publish to the Topic that you created earlier
- for Content, select the text_line_data attribute
- now the workspace will send an email whenever it is run

Parameters:
- email_to =   # To
- email_cc =   # Cc
- email_bcc =   # Bcc
- email_from =   # From
- email_replyto =   # Reply to
- email_subject =   # Subject
- email_subscriber_content =   # Content
- email_attachment_paths =   # Attachments

Input (input)
    -> Counter
Tester_2_FAILED: Junction
    -> AttributeCreator_3
Note: Rejected
AttributeCreator_3: Junction
    -> AttributeCreator_2
AttributeCreator_2
    ATTR_TABLE = SET_TO fme_rejection_code = INVALID_PARAMETER
    -> <Rejected> (output)
<Rejected> (output)
Note: Single attachment
Tester_3_FAILED: Junction
    -> JSONTemplater_2_ROOT
JSONTemplater_2_ROOT: Junction
    -> JSONTemplater_2 [ROOT]
Note: No attachment
Tester_PASSED_2: Junction
    -> Output
Note: No attachment
Output: Junction
    -> Output (output)
Output (output)

Bookmark: Parse for attachement
Counter
    SCOPE = Local
    START = 0
    DOMAIN = counter
    CNT_ATTR = _email_feature_id
    -> ParameterFetcher
ParameterFetcher
    ATTR_LIST = _email_from $(email_from) _email_replyto $(email_replyto) _email_attachment_paths $(email_attachment_paths) _email_cc $(email_cc) _email_bcc $(email_bcc)
    -> AttributeCreator
AttributeCreator
    ATTR_TABLE:
      SET_TO _email_to = $(email_to)
      SET_TO _email_subject = $(email_subject)
      SET_TO _email_subscriber_content = $(email_subscriber_content)
    -> Tester_2
Note: Test that To field contains / valid email address
Note: Reject
Tester_2
    BOOL_OP = OR
    TEST_CLAUSE = TEST @Value(_email_to) CONTAINS @
    TEST_DESCRIPTION = ""
    TEST_MODE = Automatic
    PASSED -> Tester_3
    FAILED -> Tester_2_FAILED

Bookmark: Multiple attachment string wizardy
Tester_3
    BOOL_OP = OR
    TEST_CLAUSE = TEST @Value(_email_attachment_paths) CONTAINS " "
    TEST_DESCRIPTION = ""
    TEST_MODE = Automatic
    PASSED -> SubstringExtractor
    FAILED -> Tester_3_FAILED
SubstringExtractor
    SRC_STRING = @Value(_email_attachment_paths)
    START = 1
    END = -2
    RESULT_ATTR = _email_attachment_paths
    -> StringReplacer_3
StringReplacer_3
    REGEXP = NO
    SRC_ATTRS = _email_attachment_paths
    CASE = NO
    FIND_TEXT = " "
    REPLACE_TEXT = "" ""
    NO_MATCH = _FME_NO_OP_
    -> JSONTemplater [ROOT]

Bookmark: Add multiple attachments
JSONTemplater
    ROOT_QUERY_EXPR:
      {
      "email_to": fme:get-attribute("_email_to"),
      "email_cc": fme:get-attribute("_email_cc"),
      "email_bcc": fme:get-attribute("_email_bcc"),
      "email_from": fme:get-attribute("_email_from"),
      "email_replyto": fme:get-attribute("_email_replyto"),
      "email_subject": fme:get-attribute("_email_subject"),
      "subscriber_content": fme:get-attribute("_email_subscriber_content")
      }
    VISIBLE_QUERY_VALIDATE = Yes
    RESULT_ATTRIBUTE = text_line_data
    -> Tester
Tester
    BOOL_OP = OR
    TEST_CLAUSE = TEST _email_attachment_paths ATTRIBUTE_IS_EMPTY <Unused>
    TEST_DESCRIPTION = ""
    TEST_MODE = Automatic
    PASSED -> Tester_PASSED
    FAILED -> AttributeSplitter_2
AttributeSplitter_2
    DROP_EMPTY_PARTS = No
    TRIM_OPTION = Both
    ATTR_NAME = _email_attachment_paths
    LIST_NAME = _email_attachment_path_list
    DELIMITER = " "
    -> ListExploder_2
ListExploder_2
    INDEX_ATTR = _element_index
    LIST_ATTR = _email_attachment_path_list{}
    ATTR_ACCUM_MODE = Merge List Attributes
    ATTR_CONFLICT_RES = Use List Attribute Values
    ELEMENTS -> StringConcatenator_2
StringConcatenator_2
    VAL_ATTR = _email_attachment_json
    ACTION = Create New Attribute
    PARM_LINE = "email_attachment{@Value(_element_index)}":@Value(_email_attachment_path_list)
    -> Aggregator_2
Aggregator_2
    MODE = Geometry - Assemble One Level
    SEP = ,
    AGGREGATE_TYPE = Homogeneous Collection (If Possible)
    CONCAT_ATTRS = _email_attachment_json
    GROUP_BY = _email_feature_id
    ACCUM_ATTRS_NAME = Merge Incoming Attributes
    ORDERED = No
    AGGREGATE -> StringReplacer_5
StringReplacer_5
    REGEXP = NO
    SRC_ATTRS = _email_attachment_json
    CASE = NO
    FIND_TEXT = \
    REPLACE_TEXT = \\
    NO_MATCH = _FME_NO_OP_
    -> StringReplacer_4
StringReplacer_4
    REGEXP = NO
    SRC_ATTRS = text_line_data
    CASE = NO
    FIND_TEXT = }
    REPLACE_TEXT = , @Value(_email_attachment_json)}
    NO_MATCH = _FME_NO_OP_
    -> Output (output)
Note: No attachment
Tester_PASSED: Junction
    -> Output

Bookmark: Add single attachment
JSONTemplater_2
    CONSECUTIVE_GROUPS = No
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    VISIBLE_QUERY_VALIDATE = Yes
    RESULT_ATTRIBUTE = text_line_data
    -> Tester_4
Tester_4
    BOOL_OP = OR
    TEST_CLAUSE = TEST _email_attachment_paths ATTRIBUTE_IS_EMPTY <Unused>
    TEST_DESCRIPTION = ""
    TEST_MODE = Automatic
    PASSED -> Tester_PASSED_2
    FAILED -> AttributeSplitter
AttributeSplitter
    DROP_EMPTY_PARTS = No
    TRIM_OPTION = Both
    ATTR_NAME = _email_attachment_paths
    LIST_NAME = _email_attachment_path_list
    DELIMITER = " "
    -> ListExploder
ListExploder
    INDEX_ATTR = _element_index
    LIST_ATTR = _email_attachment_path_list{}
    ATTR_ACCUM_MODE = Merge List Attributes
    ATTR_CONFLICT_RES = Use List Attribute Values
    ELEMENTS -> StringConcatenator
StringConcatenator
    VAL_ATTR = _email_attachment_json
    ACTION = Create New Attribute
    PARM_LINE = "email_attachment{@Value(_element_index)}":"@Value(_email_attachment_path_list)"
    -> Aggregator
Aggregator
    MODE = Geometry - Assemble One Level
    SEP = ,
    AGGREGATE_TYPE = Homogeneous Collection (If Possible)
    CONCAT_ATTRS = _email_attachment_json
    GROUP_BY = _email_feature_id
    ACCUM_ATTRS_NAME = Merge Incoming Attributes
    ORDERED = No
    AGGREGATE -> StringReplacer_2
StringReplacer_2
    REGEXP = NO
    SRC_ATTRS = _email_attachment_json
    CASE = NO
    FIND_TEXT = \
    REPLACE_TEXT = \\
    NO_MATCH = _FME_NO_OP_
    -> StringReplacer
StringReplacer
    REGEXP = NO
    SRC_ATTRS = text_line_data
    CASE = NO
    FIND_TEXT = }
    REPLACE_TEXT = , @Value(_email_attachment_json)}
    NO_MATCH = _FME_NO_OP_
    -> Output (output)
