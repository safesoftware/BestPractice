FME workspace BestPracticeReportGenerator2017_bothDesktopAndServer.fmw

Parameters:
- SourceDataset_FMW =   # FME Workspace (only on FME Desktop)
- Outputfolder = c:\temp   # Folder to write report to
- DestDataset_TEXTLINE_4 = C:\FMEOutput\EmailOutput.txt   # Destination Text File
- SourceDataset_TEXTLINE =   # Email data (FME Server only)
- FME_SHAREDRESOURCE_DATA = C:\temp   # FME Server Resource Data

Readers:
- TEXTLINE_1: TEXTLINE from $(SourceDataset_TEXTLINE)

Writers:
- TEXTLINE_2: TEXTLINE to $(DestDataset_TEXTLINE_4)

Creator
    NUM = 1
    GEOMTYPE = Geometry Object
    CREATED -> TestFilter
TestFilter
    DEFAULT_VALUE = <UNFILTERED>
    TEST_LIST = BOOL_OP,OR,COMPOSITE_TEST,<Unused>,TEST_CLAUSE,"TEST $(SourceDataset_TEXTLINE) NOT_ATTRIBUTE_HAS_VALUE """"",FME Desktop
    <UNFILTERED> -> FeatureReader_2 [INITIATOR]
    FME Desktop -> AttributeCreator
Note: Read the workspace from the attachment file
FeatureReader
    ATTR_ACCUM_MODE = Merge Initiator and Result
    OUTPUT_FEATURES_DISPLAY = Schema and Data Features
    ATTR_CONFLICT_RES = Use Result
    COMBINE_GEOM = Use Result
    ATTRIBUTES = Annotations,"workspace_id,annotation_id,annotation,annotation_type,fme_geometry{0}",Bookmarks,"workspace_id,bookmark_id,bookmark_name,bookmark_description,fme_geometry{0}",Breakpoints,"workspace_id,breakpoint_id,breakpoint_name,breakpoint_condition,breakpoint_test_clause,breakpoint_enabled,fme_geometry{0}",Connections,"connection_id,connection_source_id,connection_target_id,connection_source_port_desc,connection_target_port_desc,connection_enabled,connection_execution_index,connection_hidden,fme_geometry{0}",FeatureTypeFormatAttributes,"workspace_id,feature_type_id,format_attribute_name,format_attribute_type,fme_geometry{0}",FeatureTypeParameters,"workspace_id,feature_type_id,feature_type_parameter_name,feature_type_parameter_value,fme_geometry{0}",FeatureTypeUserAttributes,"workspace_id,feature_type_id,user_attribute_name,user_attribute_type,fme_geometry{0}",FileProperties,"workspace_id,file_path,file_size,creation_date,modified_date,last_run_date,fme_geometry{0}",PublishedParameters,"workspace_id,published_parameter_name,published_parameter_type,published_parameter_default_value,fme_geometry{0}",ReaderFeatureTypes,"workspace_id,reader_id,feature_type_id,reader_feature_type_qualifier,reader_feature_type_name,reader_feature_type_possible_geometries,reader_feature_type_enabled,fme_geometry{0}",ReaderHistogram,"workspace_id,reader_type,reader_count,fme_geometry{0}",ReaderParameters,"workspace_id,reader_id,reader_parameter_name,reader_parameter_value,fme_geometry{0}",Readers,"workspace_id,reader_id,reader_name,reader_keyword,reader_type,source_dataset,reader_enabled,reader_generate_build_number,fme_geometry{0}",Statistics,"workspace_id,num_published_parameters,num_annotations,num_bookmarks,num_breakpoints,num_readers,num_reader_feature_types,num_writers,num_writer_feature_types,num_transformers,num_custom_transformers,num_out_of_date_transformers,num_connections,fme_geometry{0}",TransformerHistogram,"workspace_id,transformer_type,transformer_count,fme_geometry{0}",TransformerOutputPortAttributes,"workspace_id,transformer_output_port_id,transformer_output_port_attribute_name,transformer_output_port_attribute_constant_value,transformer_output_port_attribute_enabled,fme_geometry{0}",TransformerOutputPorts,"workspace_id,transformer_id,transformer_output_port_id,transformer_output_port_name,fme_geometry{0}",TransformerParameters,"workspace_id,transformer_id,transformer_parameter_name,transformer_parameter_value,fme_geometry{0}",Transformers,"workspace_id,transformer_id,transformer_name,transformer_type,custom_transformer_parent_name,current_transformer_version,max_transformer_version,transformer_enabled,transformer_last_edit_build_number,fme_geometry{0}",WorkspaceProperties,"workspace_id,workspace_name,workspace_description,modified_build_number,category,usage,history,requirement,requirements_flag,legal,fme_geometry{0}",WriterFeatureTypes,"workspace_id,writer_id,feature_type_id,writer_feature_type_qualifier,writer_feature_type_name,writer_feature_type_possible_geometries,writer_feature_type_enabled,fme_geometry{0}",WriterHistogram,"workspace_id,writer_type,writer_count,fme_geometry{0}",WriterParameters,"workspace_id,writer_id,writer_parameter_name,writer_parameter_value,fme_geometry{0}",Writers,"workspace_id,writer_id,writer_name,writer_keyword,writer_type,destination_dataset,writer_enabled,writer_generate_build_number,fme_geometry{0}"
    FORMAT = FMW
    DATASET = @Value(email_publisher_attachment{0})
    Breakpoints -> BestPractice-FeatureInspectionAnalysis [Input:Breakpoints]
    Connections -> BestPractice-ReaderAnalysis [Input:Connections]
    FeatureTypeUserAttributes -> BestPractice:WriterAnalysis [Input:FeatureTypeUserAttributes]
    FileProperties -> FilenamePartExtractor
    PublishedParameters -> BestPractice-ReaderAnalysis [Input:PublishedParameters]
    PublishedParameters -> BestPractice:WriterAnalysis [Input:PublishedParameters]
    ReaderFeatureTypes -> BestPractice-ReaderAnalysis [Input:ReaderFeatureTypes]
    ReaderParameters -> BestPractice:WriterAnalysis [Input:ReaderParameters]
    Readers -> BestPractice-ReaderAnalysis [Input:Readers]
    Statistics -> BestPractice-StyleAnalysis [Input:Statistics]
    TransformerHistogram -> BestPractice-TransformerAnalysis [Input:TransformerHistogram]
    TransformerParameters -> BestPractice-TransformerAnalysis [Input:TransformerParameters]
    TransformerParameters -> BestPractice-PerformanceAnalysis [Input:TransformerParameters]
    Transformers -> BestPractice-TransformerAnalysis [Input:Transformers]
    Transformers -> BestPractice-PerformanceAnalysis [Input:Transformers]
    Transformers -> BestPractice:WriterAnalysis [Input:Transformers]
    WorkspaceProperties -> BestPractice-WorkspaceAnalysis [Input:WorkspaceProperties]
    WriterFeatureTypes -> BestPractice:WriterAnalysis [Input:WriterFeatureTypes]
    WriterParameters -> BestPractice:WriterAnalysis [Input:WriterParameters]
    Writers -> BestPractice:WriterAnalysis [Input:Writers]
FilenamePartExtractor
    FULLNAME_ATTR = ReportWorkspaceName
    DIRNAME_ATTR = ReportWorkspaceFolder
    SRC_ATTR = @Value(email_publisher_attachment{0})
    DIRPATH_ATTR = ReportWorkspacePath
    -> AttributeManager
Note: Create Report and File Names and Timestamp
AttributeManager
    ATTR_TABLE:
      RENAME_SET_VALUE file_size > ReportWorkspaceSize
      RENAME_SET_VALUE creation_date > ReportWorkspaceCreation
      RENAME_SET_VALUE modified_date > ReportWorkspaceModified
      RENAME_SET_VALUE last_run_date > ReportWorkspaceLastRun
      SET_TO ReportFileName = @Value(ReportWorkspaceName)-@DateTimeFormat(@DateTimeNow(),%Y%m%d%H%M%S)
      SET_TO ReportName = @Value(email_publisher_subject)
    -> AttributeFileReader
AttributeFileReader
    CHAR_ENCODING = utf-8
    FILE_NAME = @Value(email_publisher_attachment{0})
    DEST_ATTR = WorkspaceBeingAnalyzed
    -> BestPractice-ReportHeader
    -> Junction_3
BestPractice-ReportHeader
    REPORTWORKSPACE = @Value(ReportWorkspaceName)
    REPORTWORKSPACEPATH = @Value(ReportWorkspacePath)
    REPORTWORKSPACECREATION = @Value(ReportWorkspaceCreation)
    REPORTWORKSPACEMODIFIED = @Value(ReportWorkspaceModified)
    REPORTWORKSPACEFOLDER = @Value(ReportWorkspaceFolder)
    REPORTWORKSPACESIZE = @Value(ReportWorkspaceSize)
    REPORTWORKSPACELASTRUN = @Value(ReportWorkspaceLastRun)
    REPORTNAME = @Value(ReportName)
    Output:Report -> Junction_2
Note: Send email info to writer
Junction_3
    -> Junction_4
Note: Email Info
Junction_4
    -> FeatureMerger [SUPPLIER]
BestPractice-FeatureInspectionAnalysis: BestPractice-BreakpointAnalysis
    BREAKPOINT_ID = @Value(breakpoint_id)
    BREAKPOINT_NAME = @Value(breakpoint_name)
    BREAKPOINT_TEST_CLAUSE = @Value(breakpoint_test_clause)
    BREAKPOINT_CONDITION = @Value(breakpoint_condition)
    BREAKPOINT_ENABLED = @Value(breakpoint_enabled)
    WORKSPACE_ID = @Value(workspace_id)
    Output:Report -> Junction_2
    Output:Summary -> Junction
BestPractice-ReaderAnalysis
    READER_TYPE = @Value(reader_type)
    PUBLISHED_PARAMETER_NAME = @Value(published_parameter_name)
    READER_FEATURE_TYPE_QUALIFIER = @Value(reader_feature_type_qualifier)
    PUBLISHED_PARAMETER_TYPE = @Value(published_parameter_type)
    CONNECTION_SOURCE_PORT_DESC = @Value(connection_source_port_desc)
    READER_GENERATE_BUILD_NUMBER = @Value(reader_generate_build_number)
    READER_KEYWORD = @Value(reader_keyword)
    PUBLISHED_PARAMETER_DEFAULT_VALUE = @Value(published_parameter_default_value)
    READER_FEATURE_TYPE_NAME = @Value(reader_feature_type_name)
    READER_FEATURE_TYPE_ENABLED = @Value(reader_feature_type_enabled)
    FEATURE_TYPE_ID = @Value(feature_type_id)
    READER_FEATURE_TYPE_POSSIBLE_GEOMETRIES = @Value(reader_feature_type_possible_geometries)
    SOURCE_DATASET = @Value(source_dataset)
    READER_ID = @Value(reader_id)
    WORKSPACE_ID = @Value(workspace_id)
    READER_ENABLED = @Value(reader_enabled)
    READER_NAME = @Value(reader_name)
    Output:Report -> Junction_2
    Output:Summary -> Junction
BestPractice:WriterAnalysis
    WRITER_ENABLED = @Value(writer_enabled)
    READER_PARAMETER_NAME = @Value(reader_parameter_name)
    WRITER_FEATURE_TYPE_POSSIBLE_GEOMETRIES = @Value(writer_feature_type_possible_geometries)
    PUBLISHED_PARAMETER_NAME = @Value(published_parameter_name)
    PUBLISHED_PARAMETER_TYPE = @Value(published_parameter_type)
    WRITER_ID = @Value(writer_id)
    WRITER_TYPE = @Value(writer_type)
    WRITER_FEATURE_TYPE_NAME = @Value(writer_feature_type_name)
    WRITER_FEATURE_TYPE_QUALIFIER = @Value(writer_feature_type_qualifier)
    PUBLISHED_PARAMETER_DEFAULT_VALUE = @Value(published_parameter_default_value)
    WRITER_PARAMETER_NAME = @Value(writer_parameter_name)
    WRITER_PARAMETER_VALUE = @Value(writer_parameter_value)
    USER_ATTRIBUTE_TYPE = @Value(user_attribute_type)
    WRITER_NAME = @Value(writer_name)
    DESTINATION_DATASET = @Value(destination_dataset)
    WRITER_GENERATE_BUILD_NUMBER = @Value(writer_generate_build_number)
    FEATURE_TYPE_ID = @Value(feature_type_id)
    USER_ATTRIBUTE_NAME = @Value(user_attribute_name)
    TRANSFORMER_TYPE = @Value(transformer_type)
    WRITER_KEYWORD = @Value(writer_keyword)
    WORKSPACE_ID = @Value(workspace_id)
    READER_PARAMETER_VALUE = @Value(reader_parameter_value)
    WRITER_FEATURE_TYPE_ENABLED = @Value(writer_feature_type_enabled)
    Output:Report -> Junction_2
    Output:Summary -> Junction
BestPractice-PerformanceAnalysis
    CURRENT_TRANSFORMER_VERSION = @Value(current_transformer_version)
    TRANSFORMER_LAST_EDIT_BUILD_NUMBER = @Value(transformer_last_edit_build_number)
    TRANSFORMER_ID = @Value(transformer_id)
    TRANSFORMER_ENABLED = @Value(transformer_enabled)
    MAX_TRANSFORMER_VERSION = @Value(max_transformer_version)
    TRANSFORMER_PARAMETER_VALUE = @Value(transformer_parameter_value)
    TRANSFORMER_NAME = @Value(transformer_name)
    WORKSPACE_ID = @Value(workspace_id)
    TRANSFORMER_PARAMETER_NAME = @Value(transformer_parameter_name)
    TRANSFORMER_TYPE = @Value(transformer_type)
    Output:Report -> Junction_2
    Output:Summary -> Junction
BestPractice-TransformerAnalysis
    CURRENT_TRANSFORMER_VERSION = @Value(current_transformer_version)
    TRANSFORMER_TYPE_2 = @Value(transformer_type)
    TRANSFORMER_ID = @Value(transformer_id)
    TRANSFORMER_ENABLED = @Value(transformer_enabled)
    MAX_TRANSFORMER_VERSION = @Value(max_transformer_version)
    TRANSFORMER_PARAMETER_VALUE = @Value(transformer_parameter_value)
    TRANSFORMER_NAME = @Value(transformer_name)
    TRANSFORMER_COUNT = @Value(transformer_count)
    TRANSFORMER_TYPE = @Value(transformer_type)
    TRANSFORMER_PARAMETER_NAME = @Value(transformer_parameter_name)
    Output:Summary -> Junction
    Output:Report -> Junction_2
BestPractice-StyleAnalysis
    NUM_WRITERS = @Value(num_writers)
    NUM_OUT_OF_DATE_TRANSFORMERS = @Value(num_out_of_date_transformers)
    NUM_BOOKMARKS = @Value(num_bookmarks)
    NUM_BREAKPOINTS = @Value(num_breakpoints)
    NUM_CUSTOM_TRANSFORMERS = @Value(num_custom_transformers)
    NUM_ANNOTATIONS = @Value(num_annotations)
    NUM_READER_FEATURE_TYPES = @Value(num_reader_feature_types)
    NUM_WRITER_FEATURE_TYPES = @Value(num_writer_feature_types)
    NUM_PUBLISHED_PARAMETERS = @Value(num_published_parameters)
    NUM_TRANSFORMERS = @Value(num_transformers)
    WORKSPACE_ID = @Value(workspace_id)
    NUM_READERS = @Value(num_readers)
    Output:Summary -> Junction
    Output:Report -> Junction_2
BestPractice-WorkspaceAnalysis
    REQUIREMENTS_FLAG = @Value(requirements_flag)
    HISTORY = @Value(history)
    CATEGORY = @Value(category)
    MODIFIED_BUILD_NUMBER = @Value(modified_build_number)
    WORKSPACE_NAME_2 = @Value(workspace_name)
    WORKSPACE_ID = @Value(workspace_id)
    REQUIREMENT = @Value(requirement)
    USAGE = @Value(usage)
    Output:Report -> Junction_2
    Output:Summary -> Junction
Junction
    -> BestPractice-ReportSummary [Input:Summary]
BestPractice-ReportSummary
    READER_TYPE = @Value(reader_type)
    REQUIREMENTS_FLAG = @Value(requirements_flag)
    WORKSPACE_NAME_2 = @Value(workspace_name)
    CATEGORY = @Value(category)
    REQUIREMENT = @Value(requirement)
    FMEBUILDNUM = @Value(FMEBuildNum)
    SUBORDER = @Value(SubOrder)
    USAGE = @Value(usage)
    READER_FEATURE_TYPE_QUALIFIER = @Value(reader_feature_type_qualifier)
    READER_GENERATE_BUILD_NUMBER = @Value(reader_generate_build_number)
    HISTORY = @Value(history)
    EXCESSFTTEXT = @Value(ExcessFTText)
    WKSPPROPERTIESTEXT = @Value(WkspPropertiesText)
    READER_KEYWORD = @Value(reader_keyword)
    DANGLINGREADERS = @Value(DanglingReaders)
    READER_FEATURE_TYPE_NAME = @Value(reader_feature_type_name)
    MAJORBUILDTEXT = @Value(MajorBuildText)
    ERRORMSG = @Value(ErrorMsg)
    HTML_CONTENT = @Value(html_content)
    MODIFIED_BUILD_NUMBER = @Value(modified_build_number)
    READER_FEATURE_TYPE_ENABLED = @Value(reader_feature_type_enabled)
    DANGLINGREADERTEXT = @Value(DanglingReaderText)
    MAJORBUILDID = @Value(MajorBuildID)
    FEATURE_TYPE_ID = @Value(feature_type_id)
    CURRENTMAJORBUILD = @Value(CurrentMajorBuild)
    SOURCE_DATASET = @Value(source_dataset)
    WARNMSG = @Value(WarnMsg)
    READER_FEATURE_TYPE_POSSIBLE_GEOMETRIES = @Value(reader_feature_type_possible_geometries)
    NUMFEATURETYPES = @Value(NumFeatureTypes)
    WORKSPACE_ID = @Value(workspace_id)
    READER_ID = @Value(reader_id)
    READER_ENABLED = @Value(reader_enabled)
    READER_NAME = @Value(reader_name)
    MODBUILDLENGTH = @Value(ModBuildLength)
    Output:Report -> Junction_2
Junction_2
    -> BestPractice-ReportCollation [Input:Report]
BestPractice-ReportCollation
    HTML_CONTENT = @Value(html_content)
    REPORTORDER = @Value(ReportOrder)
    -> FeatureMerger [REQUESTOR]
Note: Retrieve Details of Incoming Email
FeatureMerger
    IGNORE_NULLS = No
    JOIN_KEYS = 1 1 AUTO
    ATTR_ACCUM_MODE = Merge Supplier
    MERGE_TYPE = Attributes Only
    PROCESS_DUPS = No
    REJECT_NULL_MISSING_KEYS = No
    ATTR_CONFLICT_RES = Use Requestor
    SUPPLIERS_FIRST = No
    MERGED -> TestFilter_2
    MERGED -> FeatureWriter [HTML]
    MERGED -> AttributeCopier
Note: Write HTML Report
FeatureWriter
    FORMAT = HTML
    DATASET = $(FME_SHAREDRESOURCE_DATA)\BestPractices\@Value(ReportFileName).html
    DATASET_ATTR = _dataset
    TOTAL_FEATURES_WRITTEN_ATTR = _total_features_written
    FEATURE_TYPE_LIST_ATTR = _feature_type
AttributeCopier
    ATTR_TABLE = COPY WorkspaceBeingAnalyzed > text_line_data
    -> FeatureWriter_2 [text_line]
Note: Write Workspace
FeatureWriter_2
    DATASET_ATTR = _dataset
    TEXTLINE_END_OF_LINE = System
    TEXTLINE_MIME_TYPE = text/plain
    TEXTLINE_WRITE_LAST_EOL = YES
    TEXTLINE_DESTINATION_DATASETTYPE_VALIDATION = Yes
    TEXTLINE_ENCODING = SYSTEM
    TOTAL_FEATURES_WRITTEN_ATTR = _total_features_written
    TEXTLINE_OVERWRITE_FILE = YES
    FEATURE_TYPE_LIST_ATTR = _feature_type
    FORMAT = TEXTLINE
    TEXTLINE_WRITE_UTF8_BOM = YES
    DATASET = $(FME_SHAREDRESOURCE_DATA)\BestPractices\@Value(ReportFileName).fmw
TestFilter_2
    DEFAULT_VALUE = <UNFILTERED>
    TEST_LIST = BOOL_OP,OR,COMPOSITE_TEST,<Unused>,TEST_CLAUSE,"TEST $(SourceDataset_TEXTLINE) NOT_ATTRIBUTE_HAS_VALUE """"",FME Desktop
    <UNFILTERED> -> FMEServerEmailGenerator
Note: Generate Outgoing Email
FMEServerEmailGenerator
    email_to = @Value(email_publisher_from)
    email_from = FMEBestPractice@gmail.com
    email_subscriber_content = @Value(html_content)
    email_subject = FME Best Practice Analysis Results
    -> text_line (writer TEXTLINE_2)
Note: Outgoing Email Writer
text_line (writer TEXTLINE_2)
    attributes: text_line_data buffer

Bookmark: On FME Desktop
AttributeCreator
    ATTR_TABLE = SET_TO email_publisher_attachment{0} = $(SourceDataset_FMW)
    -> AttributeCreator_3
AttributeCreator_3
    ATTR_TABLE = SET_TO _FME_SHAREDRESOURCE_DATA = @Evaluate($(Outputfolder))
    -> FeatureReader [INITIATOR]

Bookmark: On FME Server
FeatureReader_2
    OUTPUT_FEATURES_DISPLAY = Schema and Data Features
    JSON_USE_BASENAME_AS_DEFAULT_FEATURE_TYPE = No
    JSON_GEOMETRY_FORMAT = None
    ATTR_ACCUM_MODE = Only Use Result
    FORMAT = JSON
    JSON_DECODE_TEXT_STRINGS = Yes
    DATASET = $(SourceDataset_TEXTLINE)
    JSON_FLATTEN_MODE = ALL_LEVELS
    JSON_SAVE_FRAGMENTS = NO
    JSON_CLIP_TO_ENVELOPE = NO
    JSON_FEATURE_TYPE_KEY = json_featuretype
    JSON_SCAN_MODE = AUTO
    COMBINE_GEOM = Use Result
    JSON_USE_SEARCH_ENVELOPE = NO
    <OTHER> -> JSONFlattener
Note: Get input from user email to Server
text_line (reader TEXTLINE_1)
    attributes: text_line_data buffer
    -> JSONFlattener
Note: Extract the attachment filename, and email details
JSONFlattener
    NEW_ATTRIBUTES = email_publisher_subject email_publisher_attachment{0} email_publisher_from email_publisher_to email_publisher_sent email_publisher_received
    JSON_DOCUMENT = @Value(text_line_data)
    ERROR_LIST_ATTR = _json_error
    RECURSIVE = Yes
    <REJECTED> -> AttributeCreator_2
AttributeCreator_2
    ATTR_TABLE = SET_TO _FME_SHAREDRESOURCE_DATA = $(FME_SHAREDRESOURCE_DATA)\BestPractices\
    -> FeatureReader [INITIATOR]

FME custom transformer FMEServerEmailGenerator
This transformer provides an easy method for creating an email message to be sent by the FME Server Notification Service.
Input Ports
Input
This transformer will accept any feature.
Output Ports
Output
Features are output with text_line_data attribute required for the Text File Writer (see Usage Notes).
text_line_data: Contains JSON-formatted message that is required by the Email Subscription (see Usage Notes).
<Rejected>
Features will be rejected if the 'To:' field does not contain a valid email address in the form email@domain. Rejected features are output with value INVALID_PARAMETER stored in the fme_rejection_code attribute.
Parameters
To
Email address for To: field. 
Cc
Email address for Cc: field.
Bcc
Email address for Bcc: field.
From
Email address for From: field.
Reply to
Email address for Reply to: field.
Subject
Text string for subject of email.
Content
The main body of the email message.
Attachments
List of files to attach to email. For multiple files, separate filenames with a comma (e.g. file1.txt,file2.txt). File paths and features stored as attributes are both accepted.
Note: Attachments may not process if not accessible by FME Server.  
Usage Notes
Step 1. Create Topic and Email Subscription
In the FME Server Web UI, create a Topic for notifications to be sent to, and also create an Email Subscription that subscribes to this Topic.
Step 2. Create a Workspace
Once you fill out the the required paramerts for this transformer, you can send the email message in two different ways:
A. Send an email when the workspace completes:
- add a Text File Writer to the workspace
- connect FMEServerEmailGenerator Output to the Text File Writer
- publish the workspace
- register it with the Job Submitter, and/or Data Download, and/or Notification Service
- for each service, click the edit button
- expand the Notify on Job Completion section
- for Topics to Publish (Success), select the Topic created in Step 1
- for the Post Data parameter, select the Text File Writer added to the workspace
- finish publishing the workspace
- now the workspace will send an email whenever it is run through the FME Server Service you registered it with  
B. Send an email using a transformer:
- add an FMEServerNotifier transformer to your workflow
- configure it to publish to the Topic that you created earlier
- for Content, select the text_line_data attribute
- now the workspace will send an email whenever it is run

Parameters:
- email_to =   # To
- email_cc =   # Cc
- email_bcc =   # Bcc
- email_from =   # From
- email_replyto =   # Reply to
- email_subject =   # Subject
- email_subscriber_content =   # Content
- email_attachment_paths =   # Attachments

Input (input)
    -> Counter
Tester_2_FAILED: Junction
    -> AttributeCreator_3
Note: Rejected
AttributeCreator_3: Junction
    -> AttributeCreator_2
AttributeCreator_2
    ATTR_TABLE = SET_TO fme_rejection_code = INVALID_PARAMETER
    -> <Rejected> (output)
<Rejected> (output)
Note: Single attachment
Tester_3_FAILED: Junction
    -> JSONTemplater_2_ROOT
JSONTemplater_2_ROOT: Junction
    -> JSONTemplater_2 [ROOT]
Note: No attachment
Tester_PASSED_2: Junction
    -> Output
Note: No attachment
Output: Junction
    -> Output (output)
Output (output)

Bookmark: Parse for attachement
Counter
    CNT_ATTR = _email_feature_id
    START = 0
    DOMAIN = counter
    SCOPE = Local
    -> ParameterFetcher
ParameterFetcher
    ATTR_LIST = _email_from $(email_from) _email_replyto $(email_replyto) _email_attachment_paths $(email_attachment_paths) _email_cc $(email_cc) _email_bcc $(email_bcc)
    -> AttributeCreator
AttributeCreator
    ATTR_TABLE:
      SET_TO _email_to = $(email_to)
      SET_TO _email_subject = $(email_subject)
      SET_TO _email_subscriber_content = $(email_subscriber_content)
    -> Tester_2
Note: Test that To field contains / valid email address
Note: Reject
Tester_2
    TEST_CLAUSE = TEST @Value(_email_to) CONTAINS @
    TEST_DESCRIPTION = ""
    BOOL_OP = OR
    TEST_MODE = Automatic
    PASSED -> Tester_3
    FAILED -> Tester_2_FAILED

Bookmark: Multiple attachment string wizardy
Tester_3
    TEST_CLAUSE = TEST @Value(_email_attachment_paths) CONTAINS " "
    TEST_DESCRIPTION = ""
    BOOL_OP = OR
    TEST_MODE = Automatic
    PASSED -> SubstringExtractor
    FAILED -> Tester_3_FAILED
SubstringExtractor
    START = 1
    END = -2
    SRC_STRING = @Value(_email_attachment_paths)
    RESULT_ATTR = _email_attachment_paths
    -> StringReplacer_3
StringReplacer_3
    CASE = NO
    REPLACE_TEXT = "" ""
    REGEXP = NO
    NO_MATCH = _FME_NO_OP_
    FIND_TEXT = " "
    SRC_ATTRS = _email_attachment_paths
    -> JSONTemplater [ROOT]

Bookmark: Add multiple attachments
JSONTemplater
    VISIBLE_QUERY_VALIDATE = Yes
    RESULT_ATTRIBUTE = text_line_data
    ROOT_QUERY_EXPR:
      {
      "email_to": fme:get-attribute("_email_to"),
      "email_cc": fme:get-attribute("_email_cc"),
      "email_bcc": fme:get-attribute("_email_bcc"),
      "email_from": fme:get-attribute("_email_from"),
      "email_replyto": fme:get-attribute("_email_replyto"),
      "email_subject": fme:get-attribute("_email_subject"),
      "subscriber_content": fme:get-attribute("_email_subscriber_content")
      }
    -> Tester
Tester
    TEST_CLAUSE = TEST _email_attachment_paths ATTRIBUTE_IS_EMPTY <Unused>
    TEST_DESCRIPTION = ""
    BOOL_OP = OR
    TEST_MODE = Automatic
    PASSED -> Tester_PASSED
    FAILED -> AttributeSplitter_2
AttributeSplitter_2
    DROP_EMPTY_PARTS = No
    ATTR_NAME = _email_attachment_paths
    TRIM_OPTION = Both
    DELIMITER = " "
    LIST_NAME = _email_attachment_path_list
    -> ListExploder_2
ListExploder_2
    ATTR_CONFLICT_RES = Use List Attribute Values
    INDEX_ATTR = _element_index
    LIST_ATTR = _email_attachment_path_list{}
    ATTR_ACCUM_MODE = Merge List Attributes
    ELEMENTS -> StringConcatenator_2
StringConcatenator_2
    ACTION = Create New Attribute
    VAL_ATTR = _email_attachment_json
    PARM_LINE = "email_attachment{@Value(_element_index)}":@Value(_email_attachment_path_list)
    -> Aggregator_2
Aggregator_2
    AGGREGATE_TYPE = Homogeneous Collection (If Possible)
    MODE = Geometry - Assemble One Level
    CONCAT_ATTRS = _email_attachment_json
    GROUP_BY = _email_feature_id
    SEP = ,
    ACCUM_ATTRS_NAME = Merge Incoming Attributes
    ORDERED = No
    AGGREGATE -> StringReplacer_5
StringReplacer_5
    CASE = NO
    REPLACE_TEXT = \\
    REGEXP = NO
    NO_MATCH = _FME_NO_OP_
    FIND_TEXT = \
    SRC_ATTRS = _email_attachment_json
    -> StringReplacer_4
StringReplacer_4
    CASE = NO
    REPLACE_TEXT = , @Value(_email_attachment_json)}
    REGEXP = NO
    NO_MATCH = _FME_NO_OP_
    FIND_TEXT = }
    SRC_ATTRS = text_line_data
    -> Output (output)
Note: No attachment
Tester_PASSED: Junction
    -> Output

Bookmark: Add single attachment
JSONTemplater_2
    VISIBLE_QUERY_VALIDATE = Yes
    CONSECUTIVE_GROUPS = No
    RESULT_ATTRIBUTE = text_line_data
    ROOT_QUERY_EXPR:
      {
      "email_to": fme:get-attribute("_email_to"),
      "email_cc": fme:get-attribute("_email_cc"),
      "email_from": fme:get-attribute("_email_from"),
      "email_replyto": fme:get-attribute("_email_replyto"),
      "email_subject": fme:get-attribute("_email_subject"),
      "subscriber_content": fme:get-attribute("_email_subscriber_content")
      }
    -> Tester_4
Tester_4
    TEST_CLAUSE = TEST _email_attachment_paths ATTRIBUTE_IS_EMPTY <Unused>
    TEST_DESCRIPTION = ""
    BOOL_OP = OR
    TEST_MODE = Automatic
    PASSED -> Tester_PASSED_2
    FAILED -> AttributeSplitter
AttributeSplitter
    DROP_EMPTY_PARTS = No
    ATTR_NAME = _email_attachment_paths
    TRIM_OPTION = Both
    DELIMITER = " "
    LIST_NAME = _email_attachment_path_list
    -> ListExploder
ListExploder
    ATTR_CONFLICT_RES = Use List Attribute Values
    INDEX_ATTR = _element_index
    LIST_ATTR = _email_attachment_path_list{}
    ATTR_ACCUM_MODE = Merge List Attributes
    ELEMENTS -> StringConcatenator
StringConcatenator
    ACTION = Create New Attribute
    VAL_ATTR = _email_attachment_json
    PARM_LINE = "email_attachment{@Value(_element_index)}":"@Value(_email_attachment_path_list)"
    -> Aggregator
Aggregator
    AGGREGATE_TYPE = Homogeneous Collection (If Possible)
    MODE = Geometry - Assemble One Level
    CONCAT_ATTRS = _email_attachment_json
    GROUP_BY = _email_feature_id
    SEP = ,
    ACCUM_ATTRS_NAME = Merge Incoming Attributes
    ORDERED = No
    AGGREGATE -> StringReplacer_2
StringReplacer_2
    CASE = NO
    REPLACE_TEXT = \\
    REGEXP = NO
    NO_MATCH = _FME_NO_OP_
    FIND_TEXT = \
    SRC_ATTRS = _email_attachment_json
    -> StringReplacer
StringReplacer
    CASE = NO
    REPLACE_TEXT = , @Value(_email_attachment_json)}
    REGEXP = NO
    NO_MATCH = _FME_NO_OP_
    FIND_TEXT = }
    SRC_ATTRS = text_line_data
    -> Output (output)
